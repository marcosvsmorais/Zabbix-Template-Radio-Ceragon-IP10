--AIDU-MIB VERSION 6.8.0.15
AIDU-MIB DEFINITIONS ::= BEGIN

IMPORTS
--    Ipv6Address          FROM IPV6-TC
--	Counter, enterprises, Gauge, IpAddress 	FROM RFC1155-SMI
	Counter, enterprises, Gauge, IpAddress 	FROM SNMPv2-SMI
	DisplayString, ifIndex  		FROM RFC1213-MIB
	RowStatus						FROM SNMPv2-TC
	MacAddress						FROM SNMPv2-TC
	OBJECT-TYPE          			FROM SNMPv2-SMI 
	TRAP-TYPE            			FROM RFC-1215;

EnableDisable  	::= INTEGER { enable(2), disable(3) }
EnableDisableSMI2  	::= INTEGER { disable(0), enable(1) }
OffOn			::= INTEGER { off(0), on(1) }
MetricImperial	::= INTEGER { metric(0), imperial(1) }
AllowedNotAllowed ::= INTEGER {	not-allowed(0), allowed(1)}


ProgressStatus ::= INTEGER{
					ready(0),
					inProgress(1),
					success(2),
					failure(3)
				}

Severity ::= INTEGER {
			indeterminate(0),
			critical(1),
			major(2),
			minor(3),
			warning(4),
			cleared(5)
			}

-- New 6.6 declaration type.
NoYes			::= INTEGER { no(0), yes(1) }
DownUp			::= INTEGER { down(0), up(1) }

TrailIfType ::= INTEGER {
			unknown(-1),
			line(0),
			radio(1),
			stm-1-oc-3(2),
			sync(4)
			}

PmTableType ::= INTEGER {
			pm15mincurr(1),
			pm15min(2),
			pm24hrcurr(3),
			pm24hr(4)
			}

RateMbps		::= INTEGER {not-applicable(-1), n10(0), n100(1), n1000(2) }

HalfFull		::= INTEGER {not-applicable(-1), half(0), full(1), auto(2) }

BerLevel		::= INTEGER { n1e-3(2), n1e-4(3), n1e-5(4)} 

SignalLevel		::= INTEGER { n1e-6(5), n1e-7(6), n1e-8(7), n1e-9(8)}

LoopbackType	::= INTEGER {
						off(0),
						towardsLine(1),
						towardsRadio(2)
						}

QueueName		::= INTEGER {
					first-queue(0),
					second-queue(1),
					third-queue(2),
					fourth-queue(3),
					none(4)
				}

RadioId			::= INTEGER
RfuId			::= INTEGER

SwCommand ::= INTEGER{ 
				noOperation(0),
				downloadUpgradeVersion(1),
				upgrade(2),
				rollback(3),
				downgrade(4),
				downloadDowngradeVersion(5)
			}

TrailProtectedType ::= INTEGER {
				none(0),
				primary(1),
				secondary(2)
			}
			
-- 6.6.1 New emums
ClockSrc ::= INTEGER {
			local-clock(0), 
			system-clock-source(1)
		}
			
microwave-radio OBJECT IDENTIFIER ::= { enterprises 2281 }   
genEquip OBJECT IDENTIFIER ::= { microwave-radio 10}
genEquipUnit OBJECT IDENTIFIER ::= { genEquip 1}

-- 6.6.2 new enums

SlotId ::= INTEGER {
			standalone(0),
			slot1(1),
			slot2(2),
			slot3(3),
			slot4(4),
			slot5(5),
			slot6(6)
        }
	
Integrity			::= INTEGER { integrity(0), nointegrity(1) }

-- 6.7 new enums
GreenYellow ::= INTEGER {
					green(0),
					yellow(1)
		}

InputSeverity ::= INTEGER {
			indeterminate(0),
			critical(1),
			major(2),
			minor(3),
			warning(4)
			}

SwCommandTimer ::= INTEGER{ 
				noOperation(0),
				downloadUpgradeVersion(1),
				upgrade(2),
				rollback(3),
				downgrade(4),
				downloadDowngradeVersion(5),
				upgradeTimer(6),
				rollbackTimer(7),
				downgradeTimer(8),
				abortTimedInstallation(9)
			}

--- Unit information
genEquipUnitInfo OBJECT IDENTIFIER ::= { genEquipUnit 1}

genEquipLastCfgTimeStamp OBJECT-TYPE
        SYNTAX INTEGER
        ACCESS  read-only
        STATUS mandatory
        DESCRIPTION
        "This parameter represents the configuration change counter.
         On every conf. change this counter is increased by 1."
        ::= { genEquipUnitInfo 1 }

genEquipRealTimeandDate OBJECT-TYPE
        SYNTAX OCTET STRING(SIZE(8))
        ACCESS  read-write
        STATUS mandatory
        DESCRIPTION
        "This parameter specifies the real time and date
         Format 'YYYY-MM-DD,HH:MM:SS' (Hexadecimal).
         A date-time specification:

            field  octets  contents                  range
            -----  ------  --------                  -----
              1      1-2   year                      0..65536
              2       3    month                     1..12
              3       4    day                       1..31
              4       5    hour                      0..23
              5       6    minutes                   0..59
              6       7    seconds                   0..60
                           (use 60 for leap-second)
              7       8    deci-seconds              0..9

            For example, Tuesday May 26, 1992 at 1:30:15 PM EDT
            would be displayed as:        07 c8 05  1a  0d 1e 0f 00
                                         (1992  -5 -26, 13:30:15 )
         "

        ::= { genEquipUnitInfo 2 }

genEquipPMGenTime	OBJECT-TYPE
        SYNTAX 		INTEGER
        ACCESS		read-only
        STATUS		mandatory
        DESCRIPTION
"This value indicates the generation time of the Performance Monitor file.
The value is presented in time_t format."
::= { genEquipUnitInfo 3 }

genEquipInvGenTime	OBJECT-TYPE
        SYNTAX 		INTEGER
        ACCESS 		read-only
        STATUS 		mandatory
        DESCRIPTION
"This value indicates the generation time of the Inventory information file.
The inventory file holds the configuration information of the unit.
The value is presented in time_t format."
::= { genEquipUnitInfo 4 }

genEquipOperation	OBJECT-TYPE
		SYNTAX		INTEGER{
					noAction(0),
					idcHwReset(1)
					}
        ACCESS 		read-write
        STATUS 		mandatory
        DESCRIPTION
		"Enables to perform HW reset to the indoor unit."
::= { genEquipUnitInfo 5 }

genEquipMIBVersion	OBJECT-TYPE
        SYNTAX		DisplayString
        ACCESS		read-only
        STATUS		mandatory
        DESCRIPTION
"This value indicates MIB version."
::= { genEquipUnitInfo 6 }

genEquipUnitCLLI	OBJECT-TYPE
		SYNTAX		DisplayString (SIZE(0..255))
        ACCESS		read-write
        STATUS		mandatory
        DESCRIPTION
"This value represents a general purpose CLLI-like text field.
The CLLI field is attached to traps generated from this NE."
::= { genEquipUnitInfo 7 }

genEquipUnitMeasurementSystem	OBJECT-TYPE
        SYNTAX		MetricImperial
        ACCESS		read-write
        STATUS		mandatory
        DESCRIPTION
"This value represents the measurement system used by the system. (metric or imperal)."
::= { genEquipUnitInfo 8 }


genEquipUnitIduTemperature	OBJECT-TYPE
        SYNTAX		INTEGER
        ACCESS		read-only
        STATUS		mandatory
        DESCRIPTION
"This value indicates the IDU temperature, according to the measurement system chosen.
(genEquipUnitMeasurementSystem)"
::= { genEquipUnitInfo 9 }

genEquipUnitIduVoltageInput	OBJECT-TYPE
        SYNTAX		INTEGER
        ACCESS		read-only
        STATUS		mandatory
        DESCRIPTION
		"Voltages Input."
::= { genEquipUnitInfo 10 }

genEquipUnitInfoTime OBJECT IDENTIFIER ::= { genEquipUnitInfo 11}

genEquipUnitGMTHours OBJECT-TYPE
        SYNTAX INTEGER (-12..13)
        ACCESS  read-write
        STATUS mandatory
        DESCRIPTION
        "This parameter represent the offset in hours from GMT."
        ::= { genEquipUnitInfoTime 1 }

genEquipUnitGMTMins OBJECT-TYPE
        SYNTAX INTEGER (0..59)
        ACCESS  read-write
        STATUS mandatory
        DESCRIPTION
        "This parameter represents the offset in minutes from GMT."
        ::= { genEquipUnitInfoTime 2 }

genEquipUnitDaylightSavingTimeStartMonth	OBJECT-TYPE
        SYNTAX		INTEGER (1..12)
        ACCESS		read-write
        STATUS		mandatory
        DESCRIPTION
		"This parameter represents the start Month of the daylight saving time."
        ::= { genEquipUnitInfoTime 7 }      

genEquipUnitDaylightSavingTimeStartDay	OBJECT-TYPE
        SYNTAX		INTEGER (1..31)
        ACCESS		read-write
        STATUS		mandatory
        DESCRIPTION
		"This parameter represents the start Day of the daylight saving time."
        ::= { genEquipUnitInfoTime 8 }


genEquipUnitDaylightSavingTimeEndMonth	OBJECT-TYPE
        SYNTAX		INTEGER (1..12)
        ACCESS		read-write
        STATUS		mandatory
        DESCRIPTION
		"This parameter represents the end month of the daylight saving time."
        ::= { genEquipUnitInfoTime 9 }
        
genEquipUnitDaylightSavingTimeEndDay	OBJECT-TYPE
        SYNTAX		INTEGER (1..31)
        ACCESS		read-write
        STATUS		mandatory
        DESCRIPTION
		"This parameter represents the end day of the daylight saving time."
        ::= { genEquipUnitInfoTime 10 }


genEquipUnitDaylightSavingTimeOffset	OBJECT-TYPE
        SYNTAX		INTEGER (0..23)
        ACCESS		read-write
        STATUS		mandatory
        DESCRIPTION
		"Daylight saving offset hours.
		for a value different then '0', at the starting date of the daylight saving time
		the time will jump forward in this value.
		at the end date of the daylight saving time, the time will jump backwards in this value."
        ::= { genEquipUnitInfoTime 11 }
                                  
                                  
genEquipUnitIduPowerSupply1AlarmAdmin OBJECT-TYPE
        SYNTAX		EnableDisable
        ACCESS		read-write
        STATUS		mandatory
        DESCRIPTION
		"This parameter is relevant only for IDU with more than one power supply units. 
		The user can choose to disable (ignore the alarm) of one of the power supply units."
::= { genEquipUnitInfo 12 }

genEquipUnitIduPowerSupply2AlarmAdmin OBJECT-TYPE
        SYNTAX		EnableDisable
        ACCESS		read-write
        STATUS		mandatory
        DESCRIPTION
		"This parameter is relevant only for IDU with more than two power supply units. 
		The user can choose to disable (ignore the alarm) of one of the power supply units."
::= { genEquipUnitInfo 13 }


--- Unit NTP information
genEquipUnitInfoNTP OBJECT IDENTIFIER ::= { genEquipUnitInfoTime 6}

genEquipUnitInfoNTPAdmin	OBJECT-TYPE
        SYNTAX		EnableDisable 
        ACCESS		read-write
        STATUS		mandatory
        DESCRIPTION
		"This parameter represents the NTP Admin state"
::= { genEquipUnitInfoNTP 1 }

genEquipUnitInfoNTPServerIP	OBJECT-TYPE
        SYNTAX		IpAddress 
        ACCESS		read-write
        STATUS		mandatory
        DESCRIPTION
		"This parameter represents the IP address of the NTP Server"
::= { genEquipUnitInfoNTP 2 }

genEquipUnitInfoNTPStatus	OBJECT-TYPE
        SYNTAX		INTEGER {
						down(0),
						up(1)
		}
        ACCESS		read-only
        STATUS		mandatory
        DESCRIPTION
		"This parameter represents the NTP Service status"
::= { genEquipUnitInfoNTP 3 }

genEquipUnitInfoNTPSync	OBJECT-TYPE
        SYNTAX		DisplayString 
        ACCESS		read-only
        STATUS		mandatory
        DESCRIPTION
		"This parameter returns the IP address of the NTP server, with which the system is currently synchronized.
		Returned strings: 
			(i)   - the IP address of the reference NTP server, according to IPv4/v6 format.
			(ii)  - 'LOCAL' if synchronized on local clock.
			(iii) - 'N/A' if not synchronized. Valid only when admin is 'disabled'." 
::= { genEquipUnitInfoNTP 4 }

genEquipUnitInfoNTPPollInterval	OBJECT-TYPE
        SYNTAX		INTEGER (64..1024)
        ACCESS		read-only
        STATUS		mandatory
        DESCRIPTION
		"This parameter represents the NTP polling interval in minutes"
::= { genEquipUnitInfoNTP 5 }

--- Unit Serial information
genEquipUnitInventory OBJECT IDENTIFIER ::= { genEquipUnit 2}

genEquipUnitIDUSerialNumber	OBJECT-TYPE
        SYNTAX		DisplayString
        ACCESS		read-only
        STATUS		mandatory
        DESCRIPTION
		"IDU Serial number."
::= { genEquipUnitInventory 1 }

genEquipUnitIDUPartNumber	OBJECT-TYPE
        SYNTAX		DisplayString
        ACCESS		read-only
        STATUS		mandatory
        DESCRIPTION
		"IDU Part number."
::= { genEquipUnitInventory 2 }

genEquipUnitLicenseInfo OBJECT IDENTIFIER ::= { genEquipUnit 3}

genEquipUnitLicenseType	OBJECT-TYPE
        SYNTAX		INTEGER { 
						default(0), 
						normal(1), 
						demo(2) 
		}
        ACCESS		read-only
        STATUS		mandatory
        DESCRIPTION
		"The unit license type."
::= { genEquipUnitLicenseInfo 1 }

genEquipUnitLicenseCode	OBJECT-TYPE
        SYNTAX		DisplayString
        ACCESS		read-write
        STATUS		mandatory
        DESCRIPTION
		"The user license code that determines the NE license rights."
::= { genEquipUnitLicenseInfo 2 }

genEquipUnitACMLicense	OBJECT-TYPE
        SYNTAX		AllowedNotAllowed
        ACCESS		read-only
        STATUS		mandatory
        DESCRIPTION
		"The ACM rights for the NE on the current license"
::= { genEquipUnitLicenseInfo 3 }

genEquipUnitSwitchAppLicense	OBJECT-TYPE
        SYNTAX		INTEGER {
						single-pipe(0),
						switch(8)
		}
        ACCESS		read-only
        STATUS		mandatory
        DESCRIPTION
		"The switch application rights for the NE on the current license.
		Switch is either managed-switch or metro switch."
::= { genEquipUnitLicenseInfo 4 }

genEquipUnitCapacityLicense	OBJECT-TYPE
        SYNTAX		INTEGER (10..510)
        ACCESS		read-only
        STATUS		mandatory
        DESCRIPTION
		"The radio capacity allowed for the NE on the current license"
::= { genEquipUnitLicenseInfo 5 }

genEquipUnitLicenseDemoAdmin	OBJECT-TYPE
        SYNTAX		EnableDisable
        ACCESS		read-write
        STATUS		mandatory
        DESCRIPTION
		"The Admin state of the demo mode."
::= { genEquipUnitLicenseInfo 6 }

genEquipUnitLicenseDemoTimer	OBJECT-TYPE
        SYNTAX		INTEGER
        ACCESS		read-only
        STATUS		mandatory
        DESCRIPTION
		"The Demo timer in hours"
::= { genEquipUnitLicenseInfo 7}

genEquipUnitLicenseSyncU	OBJECT-TYPE
        SYNTAX		AllowedNotAllowed
        ACCESS		read-only
        STATUS		mandatory
        DESCRIPTION
		"This parameter indicates whether the synchronization unit license is allowed. 
		 This license allows configuring synchronization sources for clock distribution." 
::= { genEquipUnitLicenseInfo 8}

genEquipUnitLicenseNetworkResiliency	OBJECT-TYPE
        SYNTAX		AllowedNotAllowed
        ACCESS		read-only
        STATUS		mandatory
        DESCRIPTION
		"This parameter indicates whether the network resiliency license is allowed. 
		 This license allows configuring xSTP protocols and TDM path protection."
::= { genEquipUnitLicenseInfo 9}

genEquipUnitLicenseTDMCapacity	OBJECT-TYPE
        SYNTAX		AllowedNotAllowed
        ACCESS		read-only
        STATUS		mandatory
        DESCRIPTION
		"This parameter indicates the number of TDM trails per radio 
		 allowed by the current license, if allowed.
		 When TDM capacity license is allowed all scripts are allowed in the radio."
::= { genEquipUnitLicenseInfo 10}

genEquipUnitLicenseTDMCapacityValue	OBJECT-TYPE
        SYNTAX		INTEGER
        ACCESS		read-only
        STATUS		mandatory
        DESCRIPTION
		"This parameter indicates the number of TDM trails per radio 
		 allowed by the current license, if relevant.
		 The TDM capacity value is not relevant if the genEquipUnitLicenseTDMCapacity is not allowed."
::= { genEquipUnitLicenseInfo 11}

genEquipUnitLicensePerUsage	OBJECT-TYPE
        SYNTAX		AllowedNotAllowed
        ACCESS		read-only
        STATUS		mandatory
        DESCRIPTION
		"This parameter indicates whether the per-usage license is allowed.
		 This license allows configuring all features and causes their use to be reported to NMS.
		 If the usage license is allowed, all other licenses are not relevant, as all the licenses are open
		 for configuration."
::= { genEquipUnitLicenseInfo 12}

genEquipUnitLicenseAsymScripts	OBJECT-TYPE
        SYNTAX		AllowedNotAllowed
        ACCESS		read-only
        STATUS		mandatory
        DESCRIPTION
		"This parameter indicates whether the asymmetrical scripts license is allowed. 
		This license allows loading asymmetrical scripts."
::= { genEquipUnitLicenseInfo 13}

--- External Alarms
genEquipUnitExternalAlarms OBJECT IDENTIFIER ::= { genEquipUnit 4}

--- External Alarms - Alram Input
genEquipUnitAlarmInput OBJECT IDENTIFIER ::= { genEquipUnitExternalAlarms 1}

genEquipUnitAlarmInputTable  OBJECT-TYPE
        SYNTAX  SEQUENCE OF GenEquipUnitAlarmInputEntry
        ACCESS  not-accessible
        STATUS mandatory
        DESCRIPTION
        "External input alarm table. 
        Using the table to manage the admin state of the external input alarm (Enable or Disable it).
         Set a description and severity."
        ::= { genEquipUnitAlarmInput 1 }

genEquipUnitAlarmInputEntry OBJECT-TYPE
        SYNTAX GenEquipUnitAlarmInputEntry
        ACCESS not-accessible
        STATUS mandatory
          DESCRIPTION
         "External input alarm table. 
         Using the table to manage the admin state of the external input alarm (Enable or Disable it).
         Set a description and severity."
        INDEX { genEquipUnitAlarmInputCounter }
        ::= { genEquipUnitAlarmInputTable 1 }

GenEquipUnitAlarmInputEntry ::=
		SEQUENCE {
			genEquipUnitAlarmInputCounter
				INTEGER,
			genEquipUnitAlarmInputAdmin 
            	EnableDisableSMI2,
			genEquipUnitAlarmInputText
              DisplayString,
			genEquipUnitAlarmInputSeverity
				InputSeverity
}

genEquipUnitAlarmInputCounter		OBJECT-TYPE
		SYNTAX 		INTEGER
		ACCESS		read-only
        STATUS		mandatory
        DESCRIPTION
		"External input alarm table index."
::= { genEquipUnitAlarmInputEntry 1 }

genEquipUnitAlarmInputAdmin		OBJECT-TYPE
		SYNTAX 		EnableDisableSMI2
		ACCESS		read-write
        STATUS		mandatory
        DESCRIPTION
		"The Admin state of the External input alarm  table."
::= { genEquipUnitAlarmInputEntry 2 }

genEquipUnitAlarmInputText		OBJECT-TYPE
		SYNTAX 		DisplayString (SIZE (0..99))
		ACCESS		read-write
        STATUS		mandatory
        DESCRIPTION
		"External input alarm description."
::= { genEquipUnitAlarmInputEntry 3 }

genEquipUnitAlarmInputSeverity		OBJECT-TYPE
		SYNTAX 		InputSeverity
		ACCESS		read-write
        STATUS		mandatory
        DESCRIPTION
		"External input alarm severity."
::= { genEquipUnitAlarmInputEntry 4 }


--- External Alarms - Alarm Output
genEquipUnitAlarmOutput OBJECT IDENTIFIER ::= { genEquipUnitExternalAlarms 2}

genEquipUnitAlarmOutputTable  OBJECT-TYPE
        SYNTAX  SEQUENCE OF GenEquipUnitAlarmOutputEntry
        ACCESS  not-accessible
        STATUS mandatory
        DESCRIPTION
        "External output alarm table. using the table to manage the admin state of the external input alarm 
        , read the status and set an output group."
        ::= { genEquipUnitAlarmOutput 1 }

genEquipUnitAlarmOutputEntry OBJECT-TYPE
        SYNTAX GenEquipUnitAlarmOutputEntry
        ACCESS not-accessible
        STATUS mandatory
          DESCRIPTION
          "External output alarm table. using the table to manage the admin state of the external input alarm 
       	 , read the status and set an output group."
        INDEX { genEquipUnitAlarmOutputCounter }
        ::= { genEquipUnitAlarmOutputTable 1 }

GenEquipUnitAlarmOutputEntry ::=
		SEQUENCE {
			genEquipUnitAlarmOutputCounter
				INTEGER,
			genEquipUnitAlarmOutputAdmin 
            	INTEGER,
			genEquipUnitAlarmOutputStatus
                INTEGER,
			genEquipUnitAlarmOutputGroup
				INTEGER
}

genEquipUnitAlarmOutputCounter		OBJECT-TYPE
		SYNTAX 		INTEGER
		ACCESS		read-only
        STATUS		mandatory
        DESCRIPTION
		"External output alarm table index."
::= { genEquipUnitAlarmOutputEntry 1 }

genEquipUnitAlarmOutputAdmin		OBJECT-TYPE
		SYNTAX 		INTEGER {
						disable(0),
						enable(1),
						test(2)
		}
		ACCESS		read-write
        STATUS		mandatory
        DESCRIPTION
		"The Admin state of the External output alarm. When 'Enabled', the functionality will be:
		(i) If no alarms are raised, the N.O. (normally open) contact will be opened, 
		    while the N.C. (normally closed) contact will be connected to the COM contact.
		(ii) When an alarm is raised, or the system power is OFF, 
		the N.O will be connected to the COM contact, while the N.C. contact will remain opened.
		When 'Test' option is selected, the dry contacts behave as an alarm is raised in the system, 
		as described in case (ii) above." 
::= { genEquipUnitAlarmOutputEntry 2 }

genEquipUnitAlarmOutputStatus		OBJECT-TYPE
		SYNTAX 		INTEGER { 
				off(0), 
				on(1), 
				on-test(2) 
		} 
		ACCESS		read-only
        STATUS		mandatory
        DESCRIPTION
		"The current stauts of the External output alarm table."
		 
::= { genEquipUnitAlarmOutputEntry 3 }

genEquipUnitAlarmOutputGroup		OBJECT-TYPE
		SYNTAX 		INTEGER { 
				communication(1), 
				quality-of-service(2), 
				processing(3), 
				equipment(4), 
				environmental(5), 
				all-groups(6) 
		} 
		ACCESS		read-write
        STATUS		mandatory
        DESCRIPTION
		"The description of the group to which the external output alarm belongs."
::= { genEquipUnitAlarmOutputEntry 4 }

-- Shelf Managment
genEquipUnitShelf OBJECT IDENTIFIER ::= { genEquipUnit 5}

genEquipUnitShelfInstallation		OBJECT-TYPE
		SYNTAX 		INTEGER {
						standalone (0),
						chassisModule(1)       -- xc
		}
		ACCESS		read-only
        STATUS		mandatory
        DESCRIPTION
		"This value indicates the NE installation type (standalone or module/card within a chassis). "
::= { genEquipUnitShelf 1 }

genEquipUnitShelfModuleRole		OBJECT-TYPE
		SYNTAX 		INTEGER {
						main(0),
						extention(1)
		}
		ACCESS		read-only
        STATUS		mandatory
        DESCRIPTION
		"This value indicates the NE module role (main unit or extention)."
::= { genEquipUnitShelf 2 }

genEquipUnitShelfSlotLabel		OBJECT-TYPE
		SYNTAX 		DisplayString (SIZE(0..255))
		ACCESS		read-write
        STATUS		mandatory
        DESCRIPTION
		"Slot label is a user defined description for the module in the slot."
::= { genEquipUnitShelf 3 }

genEquipUnitShelfArchivesOperationStatus OBJECT-TYPE
		SYNTAX		ProgressStatus
		ACCESS		read-only
		STATUS		mandatory
		DESCRIPTION
		"Shelf-wide configuration archives [backup/restore] operation status.
		Used also when creating archive for unit info.
		Relevant only for main units.
		 - ready(0)
		 - inProgress(1),
		 - success(2),
		 - failure(3)"
::= { genEquipUnitShelf 4 }

genEquipUnitShelfManagmentTable  OBJECT-TYPE
        SYNTAX  SEQUENCE OF GenEquipUnitShelfManagmentEntry
        ACCESS  not-accessible
        STATUS mandatory
        DESCRIPTION
        "This table contains information about the IDUs that may be in the shelf (population, communication status, most severe alarm) and
        provides the ability to backup/restore SW for each IDU.
	    Relevant only for main units."
        ::= { genEquipUnitShelf 5 }

genEquipUnitShelfManagmentEntry OBJECT-TYPE
        SYNTAX GenEquipUnitShelfManagmentEntry
        ACCESS not-accessible
        STATUS mandatory
        DESCRIPTION
        "This table keeps the shelf information on all the modules in the shelf (population, status, most severe alarm) and
        provides the ability for backup/restore command or SW download.
		Relevant only for main units."
        INDEX { genEquipUnitShelfManagmentSlot }
        ::= { genEquipUnitShelfManagmentTable 1 }

GenEquipUnitShelfManagmentEntry ::=
		SEQUENCE {
			genEquipUnitShelfManagmentSlot
				INTEGER,
			genEquipUnitShelfManagmentSlotPopulation 
            	INTEGER,
			genEquipUnitShelfManagmentCommunicationStatus
              	INTEGER,
			genEquipUnitShelfManagmentSlotMostSevereAlarm
				Severity,
			genEquipUnitShelfManagmentMngSwCommand
				SwCommand,
			genEquipUnitShelfManagmentSlotReset
				OffOn
}

genEquipUnitShelfManagmentSlot		OBJECT-TYPE
		SYNTAX 		SlotId			
		ACCESS		read-only
        STATUS		mandatory
        DESCRIPTION
		"This value is the slot number used as an index for this table.
		Possible values:
		 - standalone(0)
		 - slot1(1)
		 - slot2(2)
		 - slot3(3)
		 - slot4(4)
		 - slot5(5)
		- slot6(6)
		Relevant only for main units."
::= { genEquipUnitShelfManagmentEntry 1 }

genEquipUnitShelfManagmentSlotPopulation		OBJECT-TYPE
		SYNTAX 		INTEGER {
						not-present(0),
						present(1)
		}
		ACCESS		read-only
        STATUS		mandatory
        DESCRIPTION
		"Slot population state, which indicates if the slot is occupied or not.
		Relevant only for main units."
::= { genEquipUnitShelfManagmentEntry 2 }

genEquipUnitShelfManagmentCommunicationStatus		OBJECT-TYPE
		SYNTAX 		INTEGER {
						communicationDown(0),	-- not alive 
						communicationUp(1)		-- alive
		}
		ACCESS		read-only
        STATUS		mandatory
        DESCRIPTION
		"This value indicates if the slot can be reached or not.
		Relevant only for main units."
::= { genEquipUnitShelfManagmentEntry 3 }

genEquipUnitShelfManagmentSlotMostSevereAlarm		OBJECT-TYPE
		SYNTAX 		Severity
		ACCESS		read-only
        STATUS		mandatory
        DESCRIPTION
		"This value is the most severe alarm for the module on this slot.
		Relevant only for main unit."
::= { genEquipUnitShelfManagmentEntry 4 }

genEquipUnitShelfManagmentMngSwCommand 		OBJECT-TYPE
		SYNTAX 		SwCommand
		ACCESS 		read-write
		STATUS 		mandatory
		DESCRIPTION
		"The command to be executed to manage SW versions.
		Relevant only for main units.
		Possible values are:
		 - noOperation(0)
		 - downloadUpgradeVersion(1)
		 - upgrade(2)
		 - rollback(3)
		 - downgrade(4)
		 - downloadDowngradeVersion(5)"
::= { genEquipUnitShelfManagmentEntry 5 }

genEquipUnitShelfManagmentSlotReset 		OBJECT-TYPE
		SYNTAX 		OffOn
		ACCESS 		read-write
		STATUS 		mandatory
		DESCRIPTION
		"This parameter Allows resetting specific unit according to genEquipUnitShelfManagmentSlot table index."
::= { genEquipUnitShelfManagmentEntry 6 }

genEquipUnitShelfReset  		OBJECT-TYPE
		SYNTAX 		OffOn
		ACCESS 		read-write
		STATUS 		mandatory
		DESCRIPTION
		"This parameter Allows resetting of entire shelf."
::= { genEquipUnitShelf 6 }

genEquipUnitshelfAllODUAdmin  		OBJECT-TYPE
		SYNTAX 		EnableDisable
		ACCESS 		read-write
		STATUS 		mandatory
		DESCRIPTION
		"The unit is configured as all outdoor unit, enable or disable it."
::= { genEquipUnitShelf 7 }

-- Protection
genEquipProtection	OBJECT IDENTIFIER ::= {genEquipUnit 6}

genEquipProtectionAdmin OBJECT-TYPE
        SYNTAX INTEGER { 
				protection1Plus1Hsb(2), 
				protectionDisable(3), 
				protection2Plus2Hsb(4), 
				protection2Plus0Hsb(5) 
		}
        ACCESS read-write
        STATUS mandatory
        DESCRIPTION
        "The Admin mode of the protection. 
         In case of protection2Plus2Hsb this parameter should be configured in 
         the main and extension slots."
        ::= { genEquipProtection 1 }

genEquipProtectionMode OBJECT-TYPE
        SYNTAX INTEGER { 
				active(0), 
				standby(1) 
		}
        ACCESS read-only
        STATUS mandatory
        DESCRIPTION
        "In protection mode, the card can be either active or standby"
        ::= { genEquipProtection 2 }

genEquipProtectionMateIPAddr OBJECT-TYPE
        SYNTAX IpAddress
        ACCESS read-only
        STATUS mandatory
        DESCRIPTION
        "Same parameter as genEquipNetworkMateIp.
        In case of 1+1 protection it is the protected card (Mate) IP address.
        In case of 2+2 protection it is the IP address of the protected unit."
        ::= { genEquipProtection 3 }

genEquipProtectionMateMACAddr OBJECT-TYPE
        SYNTAX MacAddress
        ACCESS read-only
        STATUS mandatory
        DESCRIPTION
        "In case of 1+1 protection it is protected card (Mate) MAC address
        In case of 2+2 protection it is the IP address of the protected unit."
        ::= { genEquipProtection 4 }

genEquipProtectionRadioExcessiveBERSwitch OBJECT-TYPE
        SYNTAX EnableDisable
        ACCESS read-write
        STATUS mandatory
        DESCRIPTION
        "The Admin state of an Excessive BER threshold. When enabled, crossing the Excessive BER threshold will cause 
        a protection switch."
        ::= { genEquipProtection 5 }

genEquipProtectionLockout OBJECT-TYPE
        SYNTAX OffOn
        ACCESS read-write
        STATUS mandatory
        DESCRIPTION
        "This parameter provides the ability to lock the mode of each card in the protection,
         meaning to force the fact that protection switch will not occur."
        ::= { genEquipProtection 6 }

genEquipProtectionForceSwitch OBJECT-TYPE
        SYNTAX OffOn
        ACCESS read-write
        STATUS mandatory
        DESCRIPTION
        "This parameter is a command that forces a protection switch regardless of the state of the standby card."
        ::= { genEquipProtection 7 }

genEquipProtectionManualSwitch OBJECT-TYPE
        SYNTAX OffOn
        ACCESS read-write
        STATUS mandatory
        DESCRIPTION
        "This parameter is a command that performs manaual protection switch."
        ::= { genEquipProtection 8 }

genEquipProtectionCopyToMateComand OBJECT-TYPE
        SYNTAX OffOn
        ACCESS read-write
        STATUS mandatory
        DESCRIPTION
        "Setting this parameter to On will copy configured parameters from the active to the standby unit."
        ::= { genEquipProtection 9 }

genEquipProtectionCopyToMateStatus OBJECT-TYPE
        SYNTAX ProgressStatus
        ACCESS read-only
        STATUS mandatory
        DESCRIPTION
        "This parameter represents the status of the copy-to-mate command when protection is enabled.
   		 - ready(0)
		 - inProgress(1),
		 - success(2),
		 - failure(3)"
        ::= { genEquipProtection 10 }

genEquipProtectionMultiUnitLAGAdmin OBJECT-TYPE
        SYNTAX EnableDisable
        ACCESS read-write
        STATUS mandatory
        DESCRIPTION
        "This parameter enables the Multi Unit LAG feature. 
		It can be activated only in Single Pipe configuration and only when protection is active (either 1+1 or 2+2)."
        ::= { genEquipProtection 11 }

		
--
genEquipDiversity	OBJECT IDENTIFIER ::= {genEquipUnit 7}

genEquipDiversityType OBJECT-TYPE
        SYNTAX INTEGER {
				none(1),
				space-diversity (2),
				frequency-diversity (3)
		}
        ACCESS read-write
        STATUS mandatory
        DESCRIPTION
        "this parameter sets the type of hitless diversity to be used. 
		Notice that only if protection is enabled this has any effect."
        ::= { genEquipDiversity 1 }

genEquipDiversityRevertiveMode OBJECT-TYPE
        SYNTAX INTEGER {
        			non-revertive(1),
        			revertive(2)
        }
        ACCESS read-write
        STATUS mandatory
        DESCRIPTION
        "this parameter sets whether hitless switches are revertive in the event that 
		the primary radio channel doesn't have any errors."
        ::= { genEquipDiversity 2 }

genEquipDiversityPrimaryRadio OBJECT-TYPE
        SYNTAX INTEGER {
				upper-radio(1),
				lower-radio(2)
		}
        ACCESS read-write
        STATUS mandatory
        DESCRIPTION
        "this parameter sets which IDU contains the primary radio channel to revert to."
        ::= { genEquipDiversity 3 }

genEquipDiversityRevertiveTimer OBJECT-TYPE
        SYNTAX INTEGER (1..15)
        ACCESS read-write
        STATUS mandatory
        DESCRIPTION
        "This parameter sets the amount of seconds that must pass without a failure in 
		the primary radio before doing a revertive switch."
        ::= { genEquipDiversity 4 }

genEquipDiversityForceActive OBJECT-TYPE
        SYNTAX INTEGER {
				none(0),
				local-radio(1),
				mate-radio(2)
		}
        ACCESS read-write
        STATUS mandatory
        DESCRIPTION
        "This parameter allows forcing incoming traffic to be taken from either of 
		the radios (or none) for testing purposes."
        ::= { genEquipDiversity 5 }

genEquipDiversitySwitchCounter OBJECT-TYPE
        SYNTAX INTEGER 
        ACCESS read-only
        STATUS mandatory
        DESCRIPTION
        "This parameter shows the number of hitless switches performed since last time counter was cleared."
        ::= { genEquipDiversity 6 }

genEquipDiversitySwitchCounterClear OBJECT-TYPE
        SYNTAX OffOn 
        ACCESS read-write
        STATUS mandatory
        DESCRIPTION
        "This parameter allows clearing of switch counter."
        ::= { genEquipDiversity 7 }

genEquipDiversityReceiveRadio OBJECT-TYPE
        SYNTAX INTEGER {
				lower-idu(0),
				upper-idu(1)
		}
        ACCESS read-only
        STATUS mandatory
        DESCRIPTION
        "This parameter shows from which radio the traffic is currently being taken."
        ::= { genEquipDiversity 8 }


-- Network
genEquipNetwork		OBJECT IDENTIFIER ::= {genEquip 2}

genEquipNetworkRemoteIp		OBJECT-TYPE
		SYNTAX 		IpAddress
		ACCESS		read-only
        STATUS		obsolete
        DESCRIPTION
"This value indicates the Remote IP address."
::= { genEquipNetwork 1 }

genEquipNetworkMateIp 		OBJECT-TYPE
        SYNTAX		IpAddress
        ACCESS  	read-only
        STATUS 		mandatory
        DESCRIPTION
"This value indicates the Mate IP address. (same as genEquipProtectionMateIPAddr)"
::= { genEquipNetwork 2 }

genEquipNetworkAgentIp		OBJECT-TYPE
        SYNTAX		IpAddress
        ACCESS  	read-only
        STATUS 		obsolete
        DESCRIPTION
"This value indicates the Agent IP address. (same as genEquipNetworkManagmentLocalIp)"
::= { genEquipNetwork 3 }


--- Network Managment information
genEquipNetworkManagment OBJECT IDENTIFIER ::= { genEquipNetwork 4}

genEquipNetworkManagmentLocalIp		OBJECT-TYPE
		SYNTAX 		IpAddress
		ACCESS		read-write
        STATUS		mandatory
        DESCRIPTION
		"This value indicates the local IP address. (same as genEquipNetworkAgentIp)"
::= { genEquipNetworkManagment 1 }

genEquipNetworkManagmentLocalSubnetMask		OBJECT-TYPE
		SYNTAX 		IpAddress
		ACCESS		read-write
        STATUS		mandatory
        DESCRIPTION
		"This value indicates the local subnet mask. (for example 255.255.255.0)"
::= { genEquipNetworkManagment 2 }

genEquipNetworkManagmentLocalDefaultGateway		OBJECT-TYPE
		SYNTAX 		IpAddress
		ACCESS		read-write
        STATUS		mandatory
        DESCRIPTION
		"This value indicates the local default gateway."
::= { genEquipNetworkManagment 3 }

genEquipNetworkManagmentLocalHWAddr		OBJECT-TYPE
		SYNTAX 		MacAddress
		ACCESS		read-only
        STATUS		mandatory
        DESCRIPTION
		"This value indicates the MAC Address used for management (related to the management IP address of the system)."
::= { genEquipNetworkManagment 4 }

genEquipNetworkManagmentRemoteSubnetMask		OBJECT-TYPE
		SYNTAX 		IpAddress
		ACCESS		read-write
        STATUS		obsolete
        DESCRIPTION
		"This value indicates the Remote subnet mask.(for example 255.255.255.0)"
::= { genEquipNetworkManagment 5 }

genEquipNetworkManagmentNumOfPorts		OBJECT-TYPE
		SYNTAX 		INTEGER (0..3)
		ACCESS		read-write
        STATUS		mandatory
        DESCRIPTION
		"This value indicates the number of management ports."
::= { genEquipNetworkManagment 6 }

genEquipNetworkManagmentInBandVLAN		OBJECT-TYPE
		SYNTAX 		INTEGER (1..4090)
		ACCESS		read-write
        STATUS		mandatory
        DESCRIPTION
		"This value indicates the number of in-band VLANs."
::= { genEquipNetworkManagment 7 }

genEquipNetworkManagmentPortType		OBJECT-TYPE
		SYNTAX 		INTEGER { outOfBand(0), inBand(1) }
		ACCESS		read-write
        STATUS		mandatory
        DESCRIPTION
		"This is a configurable option to use in-band or out-of-band management."
::= { genEquipNetworkManagment 8 }

genEquipNetworkManagmentPortCapacity		OBJECT-TYPE
		SYNTAX 		INTEGER { 
					n64(0), 
					n128(1), 
					n256(2), 
					n512(3), 
					n1024(4), 
					n2048(5) 
		}
		ACCESS		read-write
        STATUS		mandatory
        DESCRIPTION
		"This value indicates a limit rate for the management port capacity in kbps."
::= { genEquipNetworkManagment 9 }
		
genEquipNetworkManagmentPortAutoNegotiation		OBJECT-TYPE
		SYNTAX 		OffOn
		ACCESS		read-write
        STATUS		mandatory
        DESCRIPTION
		"Enable or disable the Auto Negotiation option, on all management ports."
::= { genEquipNetworkManagment 10 }

genEquipNetworkManagmentPortRate		OBJECT-TYPE
		SYNTAX 		INTEGER {
				not-applicable(-1), 
				n10(0), 
				n100(1)
		}
		ACCESS		read-write
        STATUS		mandatory
        DESCRIPTION
		"This value indicates the port rate in Mbps (all management ports).
		Possible values are:
		- n10(0) 10Mbps
		- n100(1) 100Mbps"
::= { genEquipNetworkManagment 11 }
		
genEquipNetworkManagmentPortDuplex		OBJECT-TYPE
		SYNTAX 		INTEGER { half(0), full(1) }
		ACCESS		read-write
        STATUS		mandatory
        DESCRIPTION
		"This value indicates the port duplex value, for all management ports."
::= { genEquipNetworkManagment 12 }

genEquipNetworkManagmentBlockMngTowardsLine		OBJECT-TYPE
		SYNTAX 		EnableDisable
		ACCESS		read-write
        STATUS		mandatory
        DESCRIPTION
		"Blocking the in-band management frames to egress via the Ethernet line interface in pipe application."
::= { genEquipNetworkManagment 13 }
		
		
--- IP Table information
genEquipNetworkIP OBJECT IDENTIFIER ::= { genEquipNetwork 5}

genEquipNetworkIPTable  OBJECT-TYPE
        SYNTAX  SEQUENCE OF GenEquipNetworkIPEntry
        ACCESS  not-accessible
        STATUS mandatory
        DESCRIPTION
        "This table keeps the information about the neighbour attributes, such as IP address, MAC address, slot,
         port number and description. It can be used by the NMS for topology discovery."
        ::= { genEquipNetworkIP 1 }

genEquipNetworkIPEntry OBJECT-TYPE
        SYNTAX GenEquipNetworkIPEntry
        ACCESS not-accessible
        STATUS mandatory
          DESCRIPTION
          "This table keeps the information about the neighbour attributes, such as IP address, MAC address, slot,
         port number and description. It can be used by the NMS for topology discovery."
        INDEX { ifIndex }
        ::= { genEquipNetworkIPTable 1 }

GenEquipNetworkIPEntry ::=
		SEQUENCE {
			genEquipNetworkIPEthernetPort
				INTEGER,
			genEquipNetworkIPPeerMacAddr 
            	OCTET STRING,
			genEquipNetworkIPPeerIPAddr
              IpAddress,
			genEquipNetworkIPPeerSlotID
				INTEGER,
			genEquipNetworkIPPeerPortNumber
				INTEGER,
			genEquipNetworkIPPeerDescr
				DisplayString,
			genEquipNetworkIPPeerNodeToNodeConnection
				EnableDisable
}

genEquipNetworkIPEthernetPort OBJECT-TYPE
        SYNTAX INTEGER
        ACCESS read-only
        STATUS mandatory
        DESCRIPTION
        "Ethernet port (local port) is the index of the table, to be taken from ifIndex."
        ::= { genEquipNetworkIPEntry 1 }

genEquipNetworkIPPeerMacAddr OBJECT-TYPE
		SYNTAX OCTET STRING
        ACCESS read-write
        STATUS mandatory
        DESCRIPTION
        "The Peer (far-end) Mac address of the managed NE (CPU) connected on the local Ethernet port"
        ::= { genEquipNetworkIPEntry 2 }

genEquipNetworkIPPeerIPAddr OBJECT-TYPE
        SYNTAX IpAddress
        ACCESS read-write
        STATUS mandatory
        DESCRIPTION
         "The Peer (far-end) IP address of the managed NE (CPU) connected on the local Ethernet port"
        ::= { genEquipNetworkIPEntry 3 }

genEquipNetworkIPPeerSlotID OBJECT-TYPE
        SYNTAX INTEGER (0..31)
        ACCESS read-write
        STATUS mandatory
        DESCRIPTION
        "The Peer (far-end) slot-id of the managed NE connected on the local Ethernet port."
        ::= { genEquipNetworkIPEntry 4 }

genEquipNetworkIPPeerPortNumber OBJECT-TYPE
        SYNTAX INTEGER (0..255)
        ACCESS read-write
        STATUS mandatory
        DESCRIPTION
        "The Peer (far-end) port number of the managed NE connected on the local Ethernet port. The port number is sequential
        starting with 1"
        ::= { genEquipNetworkIPEntry 5 }

genEquipNetworkIPPeerDescr OBJECT-TYPE
        SYNTAX DisplayString (SIZE(0..64))
        ACCESS read-write
        STATUS mandatory
        DESCRIPTION
        "User defined description for the peer port"
        ::= { genEquipNetworkIPEntry 6 }
        
genEquipNetworkIPPeerNodeToNodeConnection OBJECT-TYPE
        SYNTAX EnableDisable
        ACCESS read-write
        STATUS mandatory
        DESCRIPTION
        "Node To Node Connection.
        This column is relevant only for STM-1/OC-3 connections.
        if this parameter is enabled, it means that the STM-1/OC-3 port is connected with another microwave-radio NE,
        the STM-1/OC-3 port is not an access port, it is used by the NMS to find TDM trails."
        ::= { genEquipNetworkIPEntry 7 }
        

genEquipNetworkIPClearAllPeerInfo OBJECT-TYPE
        SYNTAX OffOn
        ACCESS read-write
        STATUS mandatory
        DESCRIPTION
        "This parameter is a command to clear the neighbor IP table info"
        ::= { genEquipNetworkIP 2 }

genEquipNetworkFloatingIp		OBJECT-TYPE
        SYNTAX		IpAddress
        ACCESS  	read-write
        STATUS 		mandatory
        DESCRIPTION
"This value indicates the floating IP used when system is in protection mode. 
This address must differ from system's own IP address (genEquipNetworkAgentIp) 
as well as mate unit's (genEquipProtectionMateIPAddr)and must be in the same subnet. 
A value of 0.0.0.0 will disable the feature."
::= { genEquipNetwork 6 }



-- Faults
genEquipFault OBJECT IDENTIFIER ::= { genEquip 3}

-- Current Alarms
genEquipCurrentAlarm OBJECT IDENTIFIER ::= {genEquipFault 1}

genEquipCurrentAlarmLastChangeCounter OBJECT-TYPE
        SYNTAX INTEGER
        ACCESS read-only
        STATUS mandatory
        DESCRIPTION
        "This counter is initialized with a random number after resest, 
        and incremented on each change in the CurrentAlarmTable"
        ::= { genEquipCurrentAlarm 1 }

genEquipCurrentAlarmTable  OBJECT-TYPE
        SYNTAX  SEQUENCE OF GenEquipCurrentAlarmEntry
        ACCESS  not-accessible
        STATUS mandatory
        DESCRIPTION
        "This table includes the current alarm (when a RAISED trap is
          sent, an alarm is added to the table, when a CLEAR trap is sent,
          the alarm is removed)."
        ::= { genEquipCurrentAlarm 2 }

genEquipCurrentAlarmEntry OBJECT-TYPE
        SYNTAX GenEquipCurrentAlarmEntry
        ACCESS not-accessible
        STATUS mandatory
          DESCRIPTION
          "Entry containing the info of current RAISED traps."
        INDEX { genEquipCurrentAlarmCounter }
        ::= { genEquipCurrentAlarmTable 1 }

GenEquipCurrentAlarmEntry ::=
		SEQUENCE {
			genEquipCurrentAlarmCounter
				INTEGER,
			genEquipCurrentAlarmRaisedTimeT 
            	INTEGER,
			genEquipCurrentAlarmId
              INTEGER,
			genEquipCurrentAlarmName
				DisplayString,
			genEquipCurrentAlarmInstance
				INTEGER,
			genEquipCurrentAlarmSeverity
				Severity,
			genEquipCurrentAlarmIfIndex
				INTEGER,
			genEquipCurrentAlarmModule
				DisplayString,
			genEquipCurrentAlarmDesc
				DisplayString,
			genEquipCurrentAlarmProbableCause
				DisplayString,
			genEquipCurrentAlarmCorrectiveActions
				DisplayString,
			genEquipCurrentAlarmState
				INTEGER,
			genEquipCurrentAlarmSlotId
				INTEGER
}

genEquipCurrentAlarmCounter OBJECT-TYPE
        SYNTAX INTEGER
        ACCESS read-only
        STATUS mandatory
        DESCRIPTION
        "A running counter of open alarms, incremented upon each new alarm.
        It is cleared after reset."
        ::= { genEquipCurrentAlarmEntry 1 }


genEquipCurrentAlarmRaisedTimeT OBJECT-TYPE
        SYNTAX INTEGER
        ACCESS read-only
        STATUS mandatory
        DESCRIPTION
        "The rasied time of this alarm.
         Time in seconds since January 1, 1970 00:00 UTC."
        ::= { genEquipCurrentAlarmEntry 2 }

genEquipCurrentAlarmId OBJECT-TYPE
        SYNTAX INTEGER
        ACCESS read-only
        STATUS mandatory
        DESCRIPTION
        "Alarm ID. List of alarm IDs is available in the MIB Ref. Guide."
        ::= { genEquipCurrentAlarmEntry 3 }

genEquipCurrentAlarmName OBJECT-TYPE
        SYNTAX DisplayString
        ACCESS read-only
        STATUS mandatory
        DESCRIPTION
        "Alarm name (the parameter and entity in the CLI) for example
        'radio/framer/radio-lof'"
        ::= { genEquipCurrentAlarmEntry 4 }

genEquipCurrentAlarmInstance OBJECT-TYPE
        SYNTAX INTEGER
        ACCESS read-only     
        STATUS mandatory
        DESCRIPTION
        "In the case of alarms that may have several appereances (at interfaces, channels, VCs, etc.), this parameter indicates the instance of the alarm."
        ::= { genEquipCurrentAlarmEntry 5 }

genEquipCurrentAlarmSeverity OBJECT-TYPE
        SYNTAX  Severity
        ACCESS  read-only
        STATUS  mandatory
        DESCRIPTION
        "The current Alarm severity
        the values can be:
         - indeterminate(0)
		 - 	critical(1)
		 - 	major(2)
		 - 	minor(3)
		 - 	warning(4)
		 - 	cleared(5)"
        DEFVAL { indeterminate }
        ::= { genEquipCurrentAlarmEntry 6 }


genEquipCurrentAlarmIfIndex OBJECT-TYPE
        SYNTAX INTEGER
        ACCESS  read-only
        STATUS mandatory
        DESCRIPTION
        "Interface Index where the alarm occurred, alarms that are
         not associated with specific interfaces will have the following value:
         For a non-interface alarm, the value is: 65001"
        ::= { genEquipCurrentAlarmEntry 7 }

genEquipCurrentAlarmModule OBJECT-TYPE
        SYNTAX  DisplayString
        ACCESS  read-only
        STATUS mandatory
        DESCRIPTION
        "The module of the alarm.
        Possible values are 'IDU' or 'RFU'."
        ::= {genEquipCurrentAlarmEntry 8}

genEquipCurrentAlarmDesc OBJECT-TYPE
        SYNTAX  DisplayString
        ACCESS  read-only
        STATUS mandatory
        DESCRIPTION
        "The alarm description (same as the description in the sent trap)."
        ::= { genEquipCurrentAlarmEntry 9}

genEquipCurrentAlarmProbableCause OBJECT-TYPE
        SYNTAX  DisplayString
        ACCESS  read-only
        STATUS mandatory
        DESCRIPTION
        "The alarm probable cause."
        ::= { genEquipCurrentAlarmEntry 10}

genEquipCurrentAlarmCorrectiveActions OBJECT-TYPE
        SYNTAX  DisplayString
        ACCESS  read-only
        STATUS mandatory
        DESCRIPTION
        "The alarm corrective actions."
        ::= { genEquipCurrentAlarmEntry 11 }

genEquipCurrentAlarmState OBJECT-TYPE
		SYNTAX		INTEGER{
					cleared(0),
					raised(1)
					}
        ACCESS read-only
        STATUS mandatory
        DESCRIPTION
        "The state of the alarm (cleared or rasied)."
        ::= { genEquipCurrentAlarmEntry 12 }

genEquipCurrentAlarmSlotId OBJECT-TYPE
		SYNTAX 		SlotId
        ACCESS read-only
        STATUS mandatory
        DESCRIPTION
        "The ID of the slot originating the alarm.
	Possible values:
		 - standalone(0)
		 - slot1(1)
		 - slot2(2)
		 - slot3(3)
		 - slot4(4)
		 - slot5(5)
		- slot6(6)"
        ::= { genEquipCurrentAlarmEntry 13 }


-- Just like current alarm
genEquipMostSevereAlarm  OBJECT-TYPE
        SYNTAX  Severity
        ACCESS read-only
        STATUS mandatory
        DESCRIPTION
        "The severity of the most severe alarm in the system" 
        ::= { genEquipCurrentAlarm 3 }

-- Traps configuration.
genEquipTrapCfg OBJECT IDENTIFIER ::= {genEquipFault 2}
        
genEquipTrapCfgMgrTable  OBJECT-TYPE
        SYNTAX  SEQUENCE OF GenEquipTrapCfgMgrEntry
        ACCESS  not-accessible
        STATUS mandatory
        DESCRIPTION
        "This table indicates the Trap manager list."
        ::= { genEquipTrapCfg 1 }

genEquipTrapCfgMgrEntry OBJECT-TYPE
        SYNTAX GenEquipTrapCfgMgrEntry
        ACCESS  not-accessible
        STATUS mandatory
        DESCRIPTION
        "Entry containing the manager IP addresses and the trap filter options."
        INDEX { genEquipTrapCfgMgrId}
        ::= { genEquipTrapCfgMgrTable 1 }

GenEquipTrapCfgMgrEntry ::=
            SEQUENCE {
        genEquipTrapCfgMgrId					INTEGER,
        genEquipTrapCfgMgrAdmin					EnableDisable,
        genEquipTrapCfgMgrIP    				IpAddress,
        genEquipTrapCfgMgrPort	            	INTEGER,
        genEquipTrapCfgMgrName					DisplayString,
		genEquipTrapCfgMgrCommunity         	DisplayString,
        genEquipTrapCfgMgrSeverityFilter		INTEGER,
        genEquipTrapCfgMgrStatusChangeFilter	OffOn,
		genEquipTrapCfgMgrCLLI 					DisplayString,
		genEquipTrapCfgMgrHeartbeatPeriod		INTEGER
	}

genEquipTrapCfgMgrId OBJECT-TYPE
        SYNTAX  INTEGER
        ACCESS  read-only
        STATUS 	mandatory
        DESCRIPTION
        "This value indicates an index of a specific manager"
        ::= { genEquipTrapCfgMgrEntry 1 }

genEquipTrapCfgMgrAdmin OBJECT-TYPE
        SYNTAX  EnableDisable
        ACCESS  read-write
        STATUS 	mandatory
        DESCRIPTION
        "This value indicates an administrative state of a specific manager.
        disable - will not send traps to this trap manager."
        ::= { genEquipTrapCfgMgrEntry 2 }
        
genEquipTrapCfgMgrIP OBJECT-TYPE
        SYNTAX  IpAddress
        ACCESS  read-write
        STATUS 	mandatory
        DESCRIPTION
        "This value indicates the manager's IP address."
        ::= { genEquipTrapCfgMgrEntry 3 }

genEquipTrapCfgMgrPort        OBJECT-TYPE
        SYNTAX  INTEGER (70..65535)
        ACCESS  read-write
        STATUS 	mandatory
        DESCRIPTION
        "The Port for sending the trap for each manager (possible values: 70-65535)"
        DEFVAL { 162 }
        ::= { genEquipTrapCfgMgrEntry 4 }

genEquipTrapCfgMgrName        OBJECT-TYPE
        SYNTAX  DisplayString (SIZE(0..30))
        ACCESS  read-write
        STATUS 	mandatory
        DESCRIPTION
        "The name of the manager configured to receive the traps"
        ::= { genEquipTrapCfgMgrEntry 5 }
        
genEquipTrapCfgMgrCommunity		OBJECT-TYPE
        SYNTAX  DisplayString (SIZE(0..30))
        ACCESS  read-write
        STATUS 	mandatory
        DESCRIPTION
        "The manager trap community configured."
        ::= { genEquipTrapCfgMgrEntry 6 }

 genEquipTrapCfgMgrSeverityFilter OBJECT-TYPE
        SYNTAX  INTEGER
        ACCESS  read-write
        STATUS 	mandatory
        DESCRIPTION
        "This is a bit mask value for masking traps according to its severity.
         There is a bit for each severity. If the relevant bit is on (1),
         the Agent will send traps with this severity. It won't send traps if the
         bit is off (0).
         The list of bits from LSB to MSB:
			Bit 1 (LSB)	- indeterminate
			Bit 2		- critical
			Bit 3		- major
			Bit 4		- minor
			Bit 5		- warning
			Bit 6		- cleared "
        ::= { genEquipTrapCfgMgrEntry 7 }
        
genEquipTrapCfgMgrStatusChangeFilter OBJECT-TYPE
        SYNTAX  OffOn
        ACCESS  read-write
        STATUS 	mandatory
        DESCRIPTION
        "This value represents the mode in which the traps are sent:
        If the filter is set to ON - only traps that change the severity of the system are sent.
        If the filter is set to OFF - all traps (that are not screened by other filters) are sent."
        ::= { genEquipTrapCfgMgrEntry 8 }


genEquipTrapCfgMgrCLLI OBJECT-TYPE
        SYNTAX DisplayString (SIZE(0..100))
        ACCESS read-write
        STATUS mandatory
        DESCRIPTION
        "Common Language Location Identifier (maximum length: 100 chars)"
        ::= { genEquipTrapCfgMgrEntry 9 }

genEquipTrapCfgMgrHeartbeatPeriod OBJECT-TYPE
        SYNTAX INTEGER (0..1440)
        ACCESS read-write
        STATUS mandatory
        DESCRIPTION
        "This item defines the interval (in minutes) between each heartbeat trap.
        A value of '0' disables this feature."
        DEFVAL { 0 }
        ::= { genEquipTrapCfgMgrEntry 10 }

-- Event Log
genEquipEventLog OBJECT IDENTIFIER ::= {genEquipFault 3}

genEquipEventLogTable  OBJECT-TYPE
        SYNTAX  SEQUENCE OF GenEquipEventLogEntry
        ACCESS  not-accessible
        STATUS mandatory
        DESCRIPTION
        "This table includes the event log."
        ::= { genEquipEventLog 1 }

genEquipEventLogEntry OBJECT-TYPE
        SYNTAX GenEquipEventLogEntry
        ACCESS not-accessible
        STATUS mandatory
          DESCRIPTION
          "Entry containing the info of the event log table."
        INDEX { genEquipEventLogCounter }
        ::= { genEquipEventLogTable 1 }

GenEquipEventLogEntry ::=
		SEQUENCE {
			genEquipEventLogCounter
				INTEGER,
			genEquipEventLogRaisedTimeT 
            	INTEGER,
			genEquipEventLogSeverity
				Severity,
			genEquipEventLogModule
				DisplayString,
			genEquipEventLogDesc
				DisplayString,
			genEquipEventLogState
				INTEGER
}

genEquipEventLogCounter OBJECT-TYPE
        SYNTAX INTEGER
        ACCESS read-only
        STATUS mandatory
        DESCRIPTION
        "The event counter."
        ::= { genEquipEventLogEntry 1 }


genEquipEventLogRaisedTimeT OBJECT-TYPE
        SYNTAX INTEGER
        ACCESS read-only
        STATUS mandatory
        DESCRIPTION
        "The rasied time of this event.
         Time in seconds since January 1, 1970 00:00 UTC. (time_t format)"
        ::= { genEquipEventLogEntry 2 }

genEquipEventLogSeverity OBJECT-TYPE
        SYNTAX  Severity
        ACCESS  read-only
        STATUS  mandatory
        DESCRIPTION
        "The event severity, possible values are:
         - indeterminate(0),
		 - critical(1)
		 - major(2)
		 - minor(3)
		 - warning(4)
		 - cleared(5)"
        ::= { genEquipEventLogEntry 3 }

genEquipEventLogModule OBJECT-TYPE
        SYNTAX  DisplayString
        ACCESS  read-only
        STATUS mandatory
        DESCRIPTION
        "The module of the event. ('IDU' or 'RFU')"
        ::= { genEquipEventLogEntry 4 }

genEquipEventLogDesc OBJECT-TYPE
        SYNTAX  DisplayString
        ACCESS  read-only
        STATUS mandatory
        DESCRIPTION
        "The event description (same as the description in the sent trap)."
        ::= { genEquipEventLogEntry 5 }

genEquipEventLogState OBJECT-TYPE
		SYNTAX		INTEGER{
					cleared(0),
					raised(1),
					event(2)
					}
        ACCESS read-only
        STATUS mandatory
        DESCRIPTION
        "The state of the event or alarm. 
        In case of alarm, 'cleard' or 'raised'.
        In case of event, 'event'."
        ::= { genEquipEventLogEntry 6 }

-- Clear event log command
genEquipEventLogClear  OBJECT-TYPE
        SYNTAX  OffOn
        ACCESS  read-write
        STATUS  mandatory
        DESCRIPTION
        "The clear event log command. If enabled, will clear the event log." 
        ::= { genEquipEventLog 2 }

-- Application last error (number and description)
genEquipFaultErrno OBJECT-TYPE
        SYNTAX  INTEGER
        ACCESS  read-only
        STATUS mandatory
        DESCRIPTION
        "The application last error number. List of Errnos are located in the MIB Ref Guide."
        ::= { genEquipFault 4 }

genEquipFaultErrDescr OBJECT-TYPE
        SYNTAX  DisplayString
        ACCESS  read-only
        STATUS mandatory
        DESCRIPTION
        "The application last error description. List of Errnos are located in the MIB Ref Guide."
        ::= { genEquipFault 5 }

		
-- Management
genEquipMng OBJECT IDENTIFIER ::= { genEquip 4}

genEquipMngSw OBJECT IDENTIFIER ::= { genEquipMng 1}

genEquipMngSwServerUrl OBJECT-TYPE
		SYNTAX 		DisplayString
		ACCESS 		read-write
		STATUS 		mandatory
		DESCRIPTION
"Remote SW Update Server URL where SW updates reside"
::= { genEquipMngSw 1 }

genEquipMngSwServerLogin 		OBJECT-TYPE
		SYNTAX 		DisplayString
		ACCESS 		read-write
		STATUS 		mandatory
		DESCRIPTION
"Remote server login"
::= { genEquipMngSw 2 }

genEquipMngSwServerPassword 	OBJECT-TYPE
		SYNTAX 		DisplayString
		ACCESS 		read-write
		STATUS 		mandatory    
		DESCRIPTION
"Remote server password"
::= { genEquipMngSw 3 }

genEquipMngSwProxyUrl 			OBJECT-TYPE
		SYNTAX 		DisplayString
		ACCESS 		read-only
		STATUS 		obsolete
		DESCRIPTION
"Proxy Server Url.
 This parameter is obsolete and should not be in used."
::= { genEquipMngSw 4 }

genEquipMngSwProxyLogin 		OBJECT-TYPE
		SYNTAX 		DisplayString
		ACCESS		read-only
		STATUS		obsolete
		DESCRIPTION
"Proxy server login
This parameter is obsolete and should not be in used."
::= { genEquipMngSw 5 }

genEquipMngSwProxyPassword		OBJECT-TYPE
		SYNTAX		DisplayString
		ACCESS		read-only
		STATUS		obsolete
		DESCRIPTION
"Proxy server password
This parameter is obsolete and should not be in used."
::= { genEquipMngSw 6 }

genEquipMngSwDownloadStatus		OBJECT-TYPE
		SYNTAX		ProgressStatus
		ACCESS		read-only
		STATUS		mandatory
		DESCRIPTION 
		"Download software status.  
		Possible values are:
		 - ready(0)
		 - inProgress(1)
		 - success(2)
		 - failure(3)"
::= { genEquipMngSw 7 }

genEquipMngSwInstallStatus 		OBJECT-TYPE
		SYNTAX		ProgressStatus
		ACCESS		read-only
		STATUS		mandatory
		DESCRIPTION
		"Install software status. 
		Possible values are:
		 - ready(0)
		 - inProgress(1)
		 - success(2)
		 - failure(3)"
::= { genEquipMngSw 8 }

genEquipMngSwCommand 		OBJECT-TYPE
		SYNTAX 		SwCommandTimer
		ACCESS 		read-write
		STATUS 		mandatory
		DESCRIPTION
		"The command that is executed to manage SW versions. 
		Depending on the value given, a different operation will be carried out involving FTP and/or version installing.
		Notice that software will be installed in all slots in a shelf and reset will be automatically carried out 
		at the end of the installation process.
		Possible values are:
		 - noOperation(0)
		 - downloadUpgradeVersion(1) - load a newer version from FTP site
		 - upgrade(2) - upgrade to newer version which has already been loaded
		 - rollback(3) - install a previously working version without downloading
		 - downgrade(4) - downgrade to an older version which has alredy been loaded
		 - downloadDowngradeVersion(5) - load an older version from FTP site
		 - upgradeTimer(6) - Starts the timer defined in genEquipMngSwInstallationTimer 
			and upon expiration upgrades to a newer version which has already been loaded.
		 - rollbackTimer(7) - Starts the timer defined in genEquipMngSwInstallationTimer 
			and upon expiration install a previously working version without downloading 
		 - downgradeTimer(7) - Starts the timer defined in genEquipMngSwInstallationTimer 
			and upon expiration downgrades to an older which has already been loaded
		 - abortTimedTnstallation(9) – stops a counting timer; the installation process will not take place. 
			Notice that it does not stop an installation process once started."
		 
::= { genEquipMngSw 9 }

genEquipMngSwInstalledIduVersion	OBJECT-TYPE
		SYNTAX 		DisplayString
		ACCESS		read-only
		STATUS		mandatory
		DESCRIPTION
		"This value indicates the Package Version of the installed IDU SW"
::= { genEquipMngSw 10 }

genEquipMngSwInstalledRfuVersion	OBJECT-TYPE
        SYNTAX  DisplayString
        ACCESS  read-only
        STATUS mandatory
        DESCRIPTION
		"This value indicates the Package version of the installed RFU SW."
::= { genEquipMngSw 11 }

-- Versions
genEquipMngSwVersions OBJECT IDENTIFIER ::= { genEquipMngSw 13}

genEquipMngSwIDUVersionsTable  OBJECT-TYPE
        SYNTAX  SEQUENCE OF GenEquipMngSwIDUVersionsEntry
        ACCESS  not-accessible
        STATUS mandatory
        DESCRIPTION
        "This table contains all IDU running versions."
        ::= { genEquipMngSwVersions 1 }

genEquipMngSwIDUVersionsEntry OBJECT-TYPE
        SYNTAX GenEquipMngSwIDUVersionsEntry
        ACCESS not-accessible
        STATUS mandatory
          DESCRIPTION
          "Entry containing the info of the IDU Versions table."
        INDEX { genEquipMngSwIDUVersionsCounter }
        ::= { genEquipMngSwIDUVersionsTable 1 }

GenEquipMngSwIDUVersionsEntry ::=
		SEQUENCE {
			genEquipMngSwIDUVersionsCounter
				INTEGER,
			genEquipMngSwIDUVersionsPackageName
				DisplayString,
			genEquipMngSwIDUVersionsTargetDevice
				DisplayString,
			genEquipMngSwIDUVersionsRunningVersion
				DisplayString,
			genEquipMngSwIDUVersionsInstalledVersion
				DisplayString,
			genEquipMngSwIDUVersionsUpgradePackage
				DisplayString,
			genEquipMngSwIDUVersionsDowngradePackage
				DisplayString
}

genEquipMngSwIDUVersionsCounter OBJECT-TYPE
        SYNTAX INTEGER
        ACCESS read-only
        STATUS mandatory
        DESCRIPTION
        "This is the index of this table."
        ::= { genEquipMngSwIDUVersionsEntry 1 }

genEquipMngSwIDUVersionsPackageName OBJECT-TYPE
        SYNTAX DisplayString
        ACCESS read-only
        STATUS mandatory
        DESCRIPTION
        "The package name"
        ::= { genEquipMngSwIDUVersionsEntry 2 }

genEquipMngSwIDUVersionsTargetDevice OBJECT-TYPE
        SYNTAX DisplayString
        ACCESS read-only
        STATUS mandatory
        DESCRIPTION
        "The Target device within the NE (i.e. Modem, FPGA, IDU)"
        ::= { genEquipMngSwIDUVersionsEntry 3 }
		
genEquipMngSwIDUVersionsRunningVersion OBJECT-TYPE
        SYNTAX DisplayString
        ACCESS read-only
        STATUS mandatory
        DESCRIPTION
        "The running version."
        ::= { genEquipMngSwIDUVersionsEntry 4 }
		
genEquipMngSwIDUVersionsInstalledVersion OBJECT-TYPE
        SYNTAX DisplayString
        ACCESS read-only
        STATUS mandatory
        DESCRIPTION
        "The installed version is similar to the running version, besides packages that are not currently running.
        Those packages will have in the running version 'N/A' while in the installed version there is a version number.
        For example, in equipment without daughter-board, some of the packages will be installed but not running."
        ::= { genEquipMngSwIDUVersionsEntry 5 }
		
genEquipMngSwIDUVersionsUpgradePackage OBJECT-TYPE
        SYNTAX DisplayString
        ACCESS read-only
        STATUS mandatory
        DESCRIPTION
        "In case the user performs an upgrade, this version will be the running/installed version"
        ::= { genEquipMngSwIDUVersionsEntry 6 }
		
genEquipMngSwIDUVersionsDowngradePackage OBJECT-TYPE
        SYNTAX DisplayString
        ACCESS read-only
        STATUS mandatory
        DESCRIPTION
        "In case the user performs downgrade, this version will be the running/installed version."
        ::= { genEquipMngSwIDUVersionsEntry 7 }


genEquipMngSwTimerTable  OBJECT-TYPE
        SYNTAX  SEQUENCE OF GenEquipMngSwTimerEntry
        ACCESS  not-accessible
        STATUS mandatory
        DESCRIPTION
        "This table contains all IDU running versions."
        ::= { genEquipMngSwVersions 2 }

genEquipMngSwTimerEntry OBJECT-TYPE
        SYNTAX GenEquipMngSwTimerEntry
        ACCESS not-accessible
        STATUS mandatory
          DESCRIPTION
          "Entry containing the info of the IDU Versions table."
        INDEX { genEquipMngSwTimerSlotNumber }
        ::= { genEquipMngSwTimerTable 1 }

GenEquipMngSwTimerEntry ::=
		SEQUENCE {
			genEquipMngSwTimerSlotNumber
				INTEGER,
			genEquipMngSwTimerInstallationTimer
				INTEGER,
			genEquipMngSwTimerTimeToInstall
				INTEGER,
			genEquipMngSwTimerTimerAbort
				INTEGER
}

genEquipMngSwTimerSlotNumber OBJECT-TYPE
        SYNTAX INTEGER (1..6)
        ACCESS read-only
        STATUS mandatory
        DESCRIPTION
        "The slot ID of the unit for this timer; 0 is for stand-alone units."
        ::= { genEquipMngSwTimerEntry 1 }
		
genEquipMngSwTimerInstallationTimer OBJECT-TYPE
        SYNTAX INTEGER (1..1440)
        ACCESS read-write
        STATUS mandatory
        DESCRIPTION
        "The timer (in minutes) for software installation operations to this unit."
        ::= { genEquipMngSwTimerEntry 2 }
		
genEquipMngSwTimerTimeToInstall OBJECT-TYPE
        SYNTAX INTEGER (1..1440)
        ACCESS read-only
        STATUS mandatory
        DESCRIPTION
        "The amount of time (in minutes) from now for the unit to perform software installation. 
		Zero denotes that no operation has been requested."
        ::= { genEquipMngSwTimerEntry 3 }
		
genEquipMngSwTimerTimerAbort OBJECT-TYPE
        SYNTAX INTEGER {
				proceed(0),
				abort (1)
		}
        ACCESS read-write
        STATUS mandatory
        DESCRIPTION
        "This parameter is used to stop the count-down to the software update action."
        ::= { genEquipMngSwTimerEntry 4 }
		
		
genEquipMngSwInstallationTimer 	OBJECT-TYPE
        SYNTAX  INTEGER (1..1440)
        ACCESS  read-write
        STATUS mandatory
        DESCRIPTION
		"The timer (in minutes) for timed software installation operations to this unit"
::= { genEquipMngSw 14 }

genEquipMngSwTimeToInstall 	OBJECT-TYPE
        SYNTAX  INTEGER (1..1440)
        ACCESS  read-only
        STATUS mandatory
        DESCRIPTION
		"The amount of time (in minutes) from now for the unit to perform software installation. 
		Zero denotes that no operation has been requested"
::= { genEquipMngSw 15 }

genEquipMngSwUpgradeCommonRfuVersion	OBJECT-TYPE
        SYNTAX  DisplayString
        ACCESS  read-only
        STATUS mandatory
        DESCRIPTION
		"This value indicates the Package version of the installed RFU SW."
::= { genEquipMngSw 16 }

genEquipMngSwDowngradeCommonRfuVersion	OBJECT-TYPE
        SYNTAX  DisplayString
        ACCESS  read-only
        STATUS mandatory
        DESCRIPTION
		"This value indicates the Package version of the installed RFU SW."
::= { genEquipMngSw 17 }


-- Management configuration
genEquipMngCfg OBJECT IDENTIFIER ::= { genEquipMng 2}

genEquipMngCfgBackupStatus 		OBJECT-TYPE
		SYNTAX		ProgressStatus
		ACCESS		read-only
		STATUS		mandatory
		DESCRIPTION
		"This parameter shows the current state of the configuration backup files creation in the IDU.
		Possible values are:
		 - ready(0)
		 - inProgress(1)
		 - success(2)
		 - failure(3)"
::= { genEquipMngCfg 1 }

genEquipMngCfgRestoreStatus 	OBJECT-TYPE
		SYNTAX		ProgressStatus
		ACCESS		read-only
		STATUS		mandatory
		DESCRIPTION
		"This parameter shows the current state of configuration restoring from downloaded backup files.
		Possible values are:
		 - ready(0)
		 - inProgress(1)
		 - success(2)
		 - failure(3)"
::= { genEquipMngCfg 2 }

genEquipMngCfgUploadStatus 		OBJECT-TYPE
		SYNTAX		ProgressStatus
		ACCESS		read-only
		STATUS		mandatory
		DESCRIPTION
		"This parameter shows the current state of configuration backup files transfer from IDU to external FTP site.
		Possible values are:
		 - ready(0)
		 - inProgress(1)
		 - success(2)
		 - failure(3)"
::= { genEquipMngCfg 3 }


genEquipMngCfgDownloadStatus		OBJECT-TYPE
		SYNTAX		ProgressStatus
		ACCESS		read-only
		STATUS		mandatory
		DESCRIPTION 
		"This parameter shows the current state of configuration backup files transfer from external FTP site to IDU.
		Possible values are:
		 - ready(0)
		 - inProgress(1)
		 - success(2)
		 - failure(3)"
::= { genEquipMngCfg 4 }

genEquipMngCfgCommand 		OBJECT-TYPE
		SYNTAX 		INTEGER{
						no-operation(0),
						backup(1),
						restore(2),
						upload(3), 
						download(4)
		}
		ACCESS 		read-write
		STATUS 		mandatory
		DESCRIPTION
	"The command to be executed to backup/restore or upload/download configuration. 
	If there is more then 1 slot in the NE, it is done for all the shelf."
::= { genEquipMngCfg 5 }

genEquipMngCfgEthernetSwitchStoreConfiguration 		OBJECT-TYPE
		SYNTAX		OffOn
		ACCESS		read-write
		STATUS		mandatory
		DESCRIPTION
		"This parameter writes the current configuration in the database. 
		This command should be called after any change to the following sections:
		-	Bridge configuration
		-	WaySide configuration
		-	Protection configuration."
::= {  genEquipMngCfg 6 }

genEquipMngCfgSetToDefaultKeepIp 		OBJECT-TYPE
		SYNTAX		OffOn
		ACCESS		read-write
		STATUS		mandatory
		DESCRIPTION
		"Set to Default configuration without changing the network parameters such as IP address, and subnet mask."
::= {  genEquipMngCfg 7 }

genEquipMngCfgCliScriptFileName 		OBJECT-TYPE
		SYNTAX		DisplayString
		ACCESS		read-write
		STATUS		mandatory
		DESCRIPTION
		"The CLI script file name to be downloaded to the NE."
::= {  genEquipMngCfg 8 }


genEquipMngFileTransfer  OBJECT IDENTIFIER ::= { genEquipMng 3}

genEquipMngFileTransferFileTypeOper 		OBJECT-TYPE
		SYNTAX		INTEGER {
						no-operation(0),
						download-configuration(1),
						download-certificate(2),
						download-warning-banner(3),
						download-cli-script(4),
						upload-configuration(5),  
						upload-csr-file(6),
						upload-unit-info(7)
		}
		ACCESS		read-write
		STATUS		mandatory
		DESCRIPTION
		"Operation for the file type to be transferred between the IDU and the external server. 
		The options with prefix 'download' are files to be transferred from the server to the IDU.  
		The options with prefix 'upload' are files to be transferred from the IDU to the server. 
		To download IDU certificate, the OIDs genEquipSecurityCfgSecurityFileName, genEquipSecurityCfgSecurityFileFormat 
		and genEquipSecurityCfgSecurityFileType should be set prior the operation of download security file. 
		To upload CSR file, the OID genEquipSecurityCfgSecurityFileName should be set prior the operation of upload CSR file.
		To download CLI string, the OID genEquipMngCfgCliScriptFileName should be set prior the operation of download cli-script.
		To download warning banner file, the OID genEquipSecurityCfgWarningBannerFName should be set prior the operation of download warning-banner."
::= {  genEquipMngFileTransfer 1 }

genEquipMngFileTransferDownloadConfigStatus 		OBJECT-TYPE
		SYNTAX		ProgressStatus
		ACCESS		read-only
		STATUS		mandatory
		DESCRIPTION
		"The operation status of download configuration, which is performed using genEquipMngFileTransferFileTypeOper"
::= {  genEquipMngFileTransfer 2 }

genEquipMngFileTransferDownloadCertificateStatus 		OBJECT-TYPE
		SYNTAX		ProgressStatus
		ACCESS		read-only
		STATUS		mandatory
		DESCRIPTION
		"The operation status of download configuration, which is performed using genEquipMngFileTransferFileTypeOper"
::= {  genEquipMngFileTransfer 3 }

genEquipMngFileTransferDownloadWarningBannerStatus 		OBJECT-TYPE
		SYNTAX		ProgressStatus
		ACCESS		read-only
		STATUS		mandatory
		DESCRIPTION
		"The operation status of download warning banner, which is performed using genEquipMngFileTransferFileTypeOper"
::= {  genEquipMngFileTransfer 4 }

genEquipMngFileTransferDownloadCliScriptStatus 		OBJECT-TYPE
		SYNTAX		ProgressStatus
		ACCESS		read-only
		STATUS		mandatory
		DESCRIPTION
		"TThe operation status of download cli script, which is performed using genEquipMngFileTransferFileTypeOper"
::= {  genEquipMngFileTransfer 5 }

genEquipMngFileTransferUploadConfigStatus 		OBJECT-TYPE
		SYNTAX		ProgressStatus
		ACCESS		read-only
		STATUS		mandatory
		DESCRIPTION
		"The operation status of upload configuration, which is performed using genEquipMngFileTransferFileTypeOper"
::= {  genEquipMngFileTransfer 6 }

genEquipMngFileTransferUploadCSRStatus 		OBJECT-TYPE
		SYNTAX		ProgressStatus
		ACCESS		read-only
		STATUS		mandatory
		DESCRIPTION
		"The operation status of upload CSR, which is performed using genEquipMngFileTransferFileTypeOper"
::= {  genEquipMngFileTransfer 7 }

genEquipMngFileTransferUploadUnitInfoStatus 		OBJECT-TYPE
		SYNTAX		ProgressStatus
		ACCESS		read-only
		STATUS		mandatory
		DESCRIPTION
		"The operation status of upload unit info, which is performed using genEquipMngFileTransferFileTypeOper"
::= {  genEquipMngFileTransfer 8 }


-- RFU
genEquipRFU	OBJECT IDENTIFIER ::= {genEquip 5}

genEquipRfuStatusTable  OBJECT-TYPE
        SYNTAX  SEQUENCE OF GenEquipRfuStatusEntry
        ACCESS  not-accessible
        STATUS mandatory
        DESCRIPTION
        "This table indicates the RFU Status Data."  
        ::= { genEquipRFU 1 }

genEquipRfuStatusEntry OBJECT-TYPE
        SYNTAX GenEquipRfuStatusEntry
        ACCESS  not-accessible
        STATUS mandatory
        DESCRIPTION
        "Entry containing the data of the RFU."
        INDEX { genEquipRfuStatusId }
        ::= { genEquipRfuStatusTable 1 }

GenEquipRfuStatusEntry ::=
            SEQUENCE {
		genEquipRfuStatusId				
			RfuId,
        genEquipRfuStatusRxLevel		
			INTEGER,
        genEquipRfuStatusTxLevel		
			INTEGER,
        genEquipRfuStatusTemperature	
			INTEGER,
        genEquipRfuStatusRunningVersion	
			DisplayString,		
		genEquipRfuStatusRFUType 
			INTEGER,
		genEquipRfuStatusRFUGrade 
			INTEGER,
		genEquipRfuStatusTxRxFreqSeparation 
			INTEGER,
		genEquipRfuStatusRFUMode 
			INTEGER,
		genEquipRfuStatusRxLevelDiversity 
			INTEGER,
		genEquipRfuStatusRxLevelCombined 
			INTEGER,
		genEquipRfuStatusAutoDelayCalStatus
		    INTEGER,
		genEquipRfuStatusRFUSerialNumber
			DisplayString,
		genEquipRfuStatusRFUPartNumber
			DisplayString,
		genEquipRfuStatusRFUmateCarrier
			INTEGER,
		genEquipRfuStatusRFUMaxTxFreq
			INTEGER,
		genEquipRfuStatusRFUMinTxFreq
			INTEGER,
		genEquipRfuStatusRFUMaxRxFreq
			INTEGER,
		genEquipRfuStatusRFUMinRxFreq
			INTEGER,
		genEquipRfuStatusInstallation
			INTEGER,
		genEquipRfuStatusDataSciErrors
			INTEGER,
		genEquipRfuStatusDeviceError
			INTEGER
	}
        
genEquipRfuStatusId OBJECT-TYPE
        SYNTAX  RfuId
        ACCESS  read-only
        STATUS 	mandatory
        DESCRIPTION
        "This value indicates an index of a specific RFU"
        ::= { genEquipRfuStatusEntry 1 }

genEquipRfuStatusRxLevel	OBJECT-TYPE
		SYNTAX		INTEGER (-199..0)
        ACCESS  	read-only
        STATUS 		mandatory
        DESCRIPTION
		"This value indicates the RFU Receive Level Status."
		::= { genEquipRfuStatusEntry 2 }

genEquipRfuStatusTxLevel	OBJECT-TYPE
        SYNTAX		INTEGER (-99..34)
        ACCESS  	read-only
        STATUS 		mandatory
        DESCRIPTION
		"This value indicates the RFU Transmit Level Status."
		::= { genEquipRfuStatusEntry 3 }

genEquipRfuStatusTemperature  OBJECT-TYPE                   
        SYNTAX  INTEGER
        ACCESS  read-only
        STATUS mandatory
        DESCRIPTION
        "This value indicates the RFU temperature. 
		The value depends on the represented measurement system.
		with genEquipUnitMeasurementSystem parameter."
        ::= { genEquipRfuStatusEntry 4 }                    

genEquipRfuStatusRunningVersion  OBJECT-TYPE
        SYNTAX  DisplayString
        ACCESS  read-only
        STATUS mandatory
        DESCRIPTION
        "This value indicates the running SW version on the RFU."
        ::= { genEquipRfuStatusEntry 5 }

		
genEquipRfuStatusRFUType OBJECT-TYPE
		SYNTAX INTEGER { 
                       	unknown(2),
                        rfu-1500p(3),
                        rfu-1500hp(5),
                        rfu-1500sp(6),
                        rfu-c(7),
                        rfu-c(9),
                        rfu-sp(11),
                        rfu-hp(12),
                        rfu-a(13),
                        rfu-d(14),
                        rfu-1500p(32),
                        rfu-1500hp(34),
                        rfu-1500sp(35),
                        rfu-c(36),
                        rfu-c(38),
                        rfu-sp(40),
                        rfu-hp(41),
                        rfu-a(42),
                        rfu-d(43)
 		}
        ACCESS  	read-only
        STATUS 		mandatory
        DESCRIPTION
		"The different types of the supported RFUs"
		::= { genEquipRfuStatusEntry 6 }

genEquipRfuStatusRFUGrade	OBJECT-TYPE
        SYNTAX		INTEGER { 
						unknown(0), 
						grade-1(1), 
						grade-2(2), 
						grade-3(3) 
		}
        ACCESS  	read-only
        STATUS 		mandatory
        DESCRIPTION
		"The grade of the RFU"
		::= { genEquipRfuStatusEntry 7 }

genEquipRfuStatusTxRxFreqSeparation	OBJECT-TYPE
        SYNTAX		INTEGER
        ACCESS  	read-only
        STATUS 		mandatory
        DESCRIPTION
		"Tx to Rx frequency separation (MHz), 
		For some RFUs the user cannot set the Tx and Rx frequencies separately (one of them affects the other one's value)."
		::= { genEquipRfuStatusEntry 8 }


genEquipRfuStatusRFUMode	OBJECT-TYPE
        SYNTAX		INTEGER {
						main(2),
						diversity(3),
						combined(4)
		}
        ACCESS  	read-only
        STATUS 		mandatory
        DESCRIPTION
		"IF combining parameter - The mode of the RFU"
		::= { genEquipRfuStatusEntry 9 }

genEquipRfuStatusRxLevelDiversity	OBJECT-TYPE
        SYNTAX		INTEGER (-199..0)
        ACCESS  	read-only
        STATUS 		mandatory
        DESCRIPTION
		"IF combining parameter - The Rx Diversity level (dBm)"
		::= { genEquipRfuStatusEntry 10 }

genEquipRfuStatusRxLevelCombined	OBJECT-TYPE
        SYNTAX		INTEGER (-199..0)
        ACCESS  	read-only
        STATUS 		mandatory
        DESCRIPTION
		"IF combining parameter - The Rx Combined level (dBm)"
		::= { genEquipRfuStatusEntry 11 }


genEquipRfuStatusAutoDelayCalStatus	OBJECT-TYPE
        SYNTAX		INTEGER {
						no-action(2),
						pass(3),
						error(4)
		}
		ACCESS  	read-only
        STATUS 		mandatory
        DESCRIPTION
		"IF combining parameter - the automatic delay calibration status. 
		Supported only for specific RFUs."
		::= { genEquipRfuStatusEntry 12 }

genEquipRfuStatusRFUSerialNumber	OBJECT-TYPE
        SYNTAX		DisplayString
        ACCESS		read-only
        STATUS		mandatory
        DESCRIPTION
		"RFU Serial number."
		::= { genEquipRfuStatusEntry 13 }

genEquipRfuStatusRFUPartNumber	OBJECT-TYPE
        SYNTAX		DisplayString
        ACCESS		read-only
        STATUS		mandatory
        DESCRIPTION
		"RFU Part number."
		::= { genEquipRfuStatusEntry 14 }

genEquipRfuStatusRFUmateCarrier	OBJECT-TYPE
        SYNTAX		INTEGER
        ACCESS		read-only
        STATUS		mandatory
        DESCRIPTION
		"The returned value indicates the slot number of the 'copartner RFU-D carrier'. 
		The returned value will be '-1' when the RFU is not RFU-D, or if the 
		'copartner RFU-D' carrier is not found."
		::= { genEquipRfuStatusEntry 15 }
              
genEquipRfuStatusRFUMaxTxFreq	OBJECT-TYPE
        SYNTAX		INTEGER
        ACCESS		read-only
        STATUS		mandatory
        DESCRIPTION
		"The maximum Tx frequency of the RFU that is allowed by the RFU."
		::= { genEquipRfuStatusEntry 16 }

genEquipRfuStatusRFUMinTxFreq	OBJECT-TYPE
        SYNTAX		INTEGER
        ACCESS		read-only
        STATUS		mandatory
        DESCRIPTION
		"The minimum Tx frequency of the RFU that is allowed by the RFU."
		::= { genEquipRfuStatusEntry 17 }		

genEquipRfuStatusRFUMaxRxFreq	OBJECT-TYPE
        SYNTAX		INTEGER
        ACCESS		read-only
        STATUS		mandatory
        DESCRIPTION
		"The maximum Rx frequency of the RFU that is allowed by the RFU."
		::= { genEquipRfuStatusEntry 18 }

genEquipRfuStatusRFUMinRxFreq	OBJECT-TYPE
        SYNTAX		INTEGER
        ACCESS		read-only
        STATUS		mandatory
        DESCRIPTION
		"The minimum Rx frequency of the RFU that is allowed by the RFU."
		::= { genEquipRfuStatusEntry 19 }
		
genEquipRfuStatusInstallation	OBJECT-TYPE
        SYNTAX		INTEGER {
        					split-mount(0), 
        					all-indoor(1)
        			}
        ACCESS		read-only
        STATUS		mandatory
        DESCRIPTION
		"Returns 'all-indoor' or 'split' according to the RFU installation."
		::= { genEquipRfuStatusEntry 20 }             

genEquipRfuStatusDataSciErrors	OBJECT-TYPE
        SYNTAX		INTEGER 
        ACCESS		read-only
        STATUS		mandatory
        DESCRIPTION
		"Data Sci Errors"
		::= { genEquipRfuStatusEntry 21 }             

genEquipRfuStatusDeviceError	OBJECT-TYPE
        SYNTAX		INTEGER 
        ACCESS		read-only
        STATUS		mandatory
        DESCRIPTION
		"Status Device Error"
		::= { genEquipRfuStatusEntry 22 }             

		
-- RFU CFG TABLE 
genEquipRfuCfgTable  OBJECT-TYPE
        SYNTAX  SEQUENCE OF GenEquipRfuCfgEntry
        ACCESS  not-accessible
        STATUS mandatory
        DESCRIPTION
        "This table indicates the RFU Configuration."
        ::= { genEquipRFU 2 }

genEquipRfuCfgEntry OBJECT-TYPE
        SYNTAX GenEquipRfuCfgEntry
        ACCESS  not-accessible
        STATUS mandatory
        DESCRIPTION
        "This table indicates the RFU Configuration."
        INDEX { genEquipRfuCfgId }
        ::= { genEquipRfuCfgTable 1 }

GenEquipRfuCfgEntry ::=
            SEQUENCE {
		genEquipRfuCfgId			
			RfuId,
		genEquipRfuCfgMaxTxLevel	
			INTEGER,
		genEquipRfuCfgTxFreq 
			INTEGER,
		genEquipRfuCfgRxFreq 
			INTEGER,
		genEquipRfuCfgATPCAdmin 
			EnableDisable,
		genEquipRfuCfgATPCRefRSL 
			INTEGER,
		genEquipRfuCfgMuteTx 
			EnableDisable,
		genEquipRfuCfgRSLConnSrc 
			INTEGER,
		genEquipRfuCfgDelayCal 
			INTEGER,
		genEquipRfuCfgLoopback 
			LoopbackType,
		genEquipRfuCfgLogAdmin
			EnableDisable,
		genEquipRfuCfgClearComDeviceError
			OffOn,
		genEquipRfuCfgGreenModeAdmin
			EnableDisable,
		genEquipRfuCfgGreenModeReferenceLevel
			INTEGER,
		genEquipRfuCfgATPCOverrideTxLevel
			INTEGER,
		genEquipRfuCfgATPCOverrideTimeout
			INTEGER,
		genEquipRfuCfgATPCOverrideTimerCounter
			INTEGER,
		genEquipRfuCfgATPCOverrideTimerCancel
			OffOn
	}
        
genEquipRfuCfgId OBJECT-TYPE
        SYNTAX  RfuId
        ACCESS  read-only
        STATUS 	mandatory
        DESCRIPTION
        "This value indicates an index of a specific RFU"
        ::= { genEquipRfuCfgEntry 1 }

genEquipRfuCfgMaxTxLevel		OBJECT-TYPE
		SYNTAX 		INTEGER (-50..34)
		ACCESS		read-write
        STATUS		mandatory
        DESCRIPTION
		"This value indicates the RFU Maximum Transmit Level Configuration."
		::= { genEquipRfuCfgEntry 2 }
		
genEquipRfuCfgTxFreq	OBJECT-TYPE
        SYNTAX		INTEGER
        ACCESS  	read-write
        STATUS 		mandatory
        DESCRIPTION
		"Tx Frequency configuration (Mhz)"
		::= { genEquipRfuCfgEntry 3 }

genEquipRfuCfgRxFreq	OBJECT-TYPE
        SYNTAX		INTEGER
        ACCESS  	read-write
        STATUS 		mandatory
        DESCRIPTION
		"Rx Frequency configuration (Mhz)"
		::= { genEquipRfuCfgEntry 4 }

genEquipRfuCfgATPCAdmin	OBJECT-TYPE
        SYNTAX		EnableDisable
        ACCESS  	read-write
        STATUS 		mandatory
        DESCRIPTION
		"ATPC configuration - Admin mode
		Possible values: 
		 - enable(2)
		 - disable(3)"
		::= { genEquipRfuCfgEntry 5 }

genEquipRfuCfgATPCRefRSL	OBJECT-TYPE
        SYNTAX		INTEGER (-70..-30)
        ACCESS  	read-write
        STATUS 		mandatory
        DESCRIPTION
		"ATPC configuration - reference RSL level (dBm)"
		::= { genEquipRfuCfgEntry 6 }


genEquipRfuCfgMuteTx	OBJECT-TYPE
        SYNTAX		EnableDisable
        ACCESS  	read-write
        STATUS 		mandatory
        DESCRIPTION
		"Mute the Tx output of the RFU
		Possible values: 
		 - enable(2)
		 - disable(3)"
		::= { genEquipRfuCfgEntry 7 }


genEquipRfuCfgRSLConnSrc	OBJECT-TYPE
        SYNTAX		INTEGER {
						main(2),
						diversity(3)
		}
        ACCESS  	read-write
        STATUS 		mandatory
        DESCRIPTION
		"IF combining - RFU RSL (Received Signal Level) connector source "
		::= { genEquipRfuCfgEntry 8 }

genEquipRfuCfgDelayCal	OBJECT-TYPE
        SYNTAX		INTEGER (-130..130)
        ACCESS  	read-write
        STATUS 		mandatory
        DESCRIPTION
		"IF combining - Delay calibration"
		::= { genEquipRfuCfgEntry 9 }

genEquipRfuCfgLoopback	OBJECT-TYPE
        SYNTAX		INTEGER {
						off(0),
						towardsSystem(1)
						}
        ACCESS  	read-write
        STATUS 		mandatory
        DESCRIPTION
		"RFU RF loopback command"
		::= { genEquipRfuCfgEntry 10 }
		
genEquipRfuCfgLogAdmin	OBJECT-TYPE
        SYNTAX		EnableDisable
        ACCESS  	read-write
        STATUS 		mandatory
        DESCRIPTION
		"RFU internal log file admin
		Possible values: 
		 - enable(2)
		 - disable(3)"
		::= { genEquipRfuCfgEntry 11 }

genEquipRfuCfgClearComDeviceError	OBJECT-TYPE
        SYNTAX		OffOn
        ACCESS		read-write
        STATUS		mandatory
        DESCRIPTION
		"Clear Com device Error."
		::= { genEquipRfuCfgEntry 12 }             

genEquipRfuCfgGreenModeAdmin	OBJECT-TYPE
        SYNTAX		EnableDisable
        ACCESS  	read-write
        STATUS 		mandatory
        DESCRIPTION
		"Enables/disables RFU green mode.
		This mode will minimize power consumption while ensuring the highest transmission power 
		possible to get an RSL not higher than defined in the reference level genEquipRfuCfgGreenModeReferenceLevel"
		::= { genEquipRfuCfgEntry 13 }
		
genEquipRfuCfgGreenModeReferenceLevel	OBJECT-TYPE
        SYNTAX		INTEGER
        ACCESS  	read-write
        STATUS 		mandatory
        DESCRIPTION
		"RSL reference level (in dB) for green mode operation"
		::= { genEquipRfuCfgEntry 14 }

genEquipRfuCfgATPCOverrideTxLevel	OBJECT-TYPE
        SYNTAX		INTEGER (-50..34)
        ACCESS  	read-write
        STATUS 		mandatory
        DESCRIPTION
		"This parameter configures the default transmission signal level in case of ATPC override due to expiration 
		of maximum power timer as defined in genEquipRfuCfgATPCOverrideTimeout."
		::= { genEquipRfuCfgEntry 15 }

genEquipRfuCfgATPCOverrideTimeout	OBJECT-TYPE
        SYNTAX		INTEGER (0..600)
        ACCESS  	read-write
        STATUS 		mandatory
        DESCRIPTION
		"This parameter configures the timer to be counted while in ATPC in case of maximum power transmission. 
		If this timer expires, the system will transmit at a default level defined in genEquipRfuCfgATPCOverrideTxLevel"
		::= { genEquipRfuCfgEntry 16 }

genEquipRfuCfgATPCOverrideTimerCounter	OBJECT-TYPE
        SYNTAX		INTEGER (0..600)
        ACCESS  	read-only
        STATUS 		mandatory
        DESCRIPTION
		"This parameter shows the time left in the timer defined by genEquipRfuCfgATPCOverrideTxLevel"
		::= { genEquipRfuCfgEntry 17 }

genEquipRfuCfgATPCOverrideTimerCancel	OBJECT-TYPE
        SYNTAX		OffOn
        ACCESS  	read-write
        STATUS 		mandatory
        DESCRIPTION
		"Setting this parameter to ON will cancel the ATPC override mode. 
		This will only be effective while in this mode ��������������������������� i.e. the system had been transmitting 
		at maximum power for a time longer than defined in genEquipRfuCfgATPCOverrideTxLevel 
		and now is transmitting at the default level defined in genEquipRfuCfgATPCOverrideTxLevel. 
		Following execution, the system will go back to normal ATPC operating mode"
		::= { genEquipRfuCfgEntry 18 }

		
-- Upload table
genEquipRfuUploadTable  OBJECT-TYPE
        SYNTAX  SEQUENCE OF GenEquipRfuUploadEntry
        ACCESS  not-accessible
        STATUS mandatory
        DESCRIPTION
        "RFU Upload Data table."
        ::= { genEquipRFU 3 }

genEquipRfuUploadEntry OBJECT-TYPE
        SYNTAX GenEquipRfuUploadEntry
        ACCESS  not-accessible
        STATUS mandatory
        DESCRIPTION
        "Entry containing the data of the RFU."
        INDEX { genEquipRfuUploadId }
        ::= { genEquipRfuUploadTable 1 }

GenEquipRfuUploadEntry ::=
            SEQUENCE {
		genEquipRfuUploadId					RadioId,
		genEquipRfuUploadSwCommand			INTEGER,
	    genEquipRfuUploadSwStatus			INTEGER,
	    genEquipRfuUploadCounter			INTEGER
	}
        
genEquipRfuUploadId OBJECT-TYPE
        SYNTAX  RadioId
        ACCESS  read-only
        STATUS 	mandatory
        DESCRIPTION
        "This value indicates an index of a specific RFU"
        ::= { genEquipRfuUploadEntry 1 }

genEquipRfuUploadSwCommand  OBJECT-TYPE
        SYNTAX 		INTEGER{
					uploadSW(1),
					noOperation(2)
					}
        ACCESS  read-write
        STATUS mandatory
        DESCRIPTION
        "This value initiates SW upload to the RFU."
        ::= { genEquipRfuUploadEntry 2 }

genEquipRfuUploadSwStatus  OBJECT-TYPE
        SYNTAX  INTEGER{
				noLoad(0),
				loadError(1),
				loadStart(2),
				loadSendBlock(3),
				loadDone(5)					
        }
        ACCESS  read-only
        STATUS mandatory
        DESCRIPTION
        "This value indicates the status of the SW load operation on the RFU."
        ::= { genEquipRfuUploadEntry 3 }    
        
genEquipRfuUploadCounter  OBJECT-TYPE
        SYNTAX  INTEGER
        ACCESS  read-only
        STATUS mandatory
        DESCRIPTION
        "This parameter shows the progress (in blocks) of RFU software download"
        ::= { genEquipRfuUploadEntry 4 }






      
-- Performance Monitoring Tables

genEquipPM	OBJECT IDENTIFIER ::= {genEquip 6}

genEquipPmRfu	OBJECT IDENTIFIER ::= {genEquipPM 1}

genEquipPmRfuCommon	OBJECT IDENTIFIER ::= {genEquipPmRfu 1}

genEquipPmRfuCommonSL15minTable  OBJECT-TYPE
        SYNTAX  SEQUENCE OF GenEquipPmRfuCommonSL15minEntry
        ACCESS  not-accessible
        STATUS mandatory
        DESCRIPTION
        "This table indicates the RFU Signal Level PM data."
        ::= { genEquipPmRfuCommon 1 }

genEquipPmRfuCommonSL15minEntry OBJECT-TYPE
        SYNTAX GenEquipPmRfuCommonSL15minEntry
        ACCESS  not-accessible
        STATUS mandatory
        DESCRIPTION
        "Entry containing the data of the RFU SL PM."
        INDEX { genEquipPmRfuCommonSL15minId }
        ::= { genEquipPmRfuCommonSL15minTable 1 }

GenEquipPmRfuCommonSL15minEntry ::=
            SEQUENCE {
		genEquipPmRfuCommonSL15minId			INTEGER,
		genEquipPmRfuCommonSL15minIfIndex		INTEGER,
        genEquipPmRfuCommonSL15minTimeAndDate	DisplayString,
        genEquipPmRfuCommonSL15minMinRsl		INTEGER,
        genEquipPmRfuCommonSL15minMaxRsl		INTEGER,
        genEquipPmRfuCommonSL15minRslExceed1	INTEGER,
        genEquipPmRfuCommonSL15minRslExceed2	INTEGER,
        genEquipPmRfuCommonSL15minMinTsl		INTEGER,
        genEquipPmRfuCommonSL15minMaxTsl		INTEGER,
        genEquipPmRfuCommonSL15minTslExceed		INTEGER,
        genEquipPmRfuCommonSL15minIDF			Integrity
	}

genEquipPmRfuCommonSL15minId OBJECT-TYPE
        SYNTAX  INTEGER
        ACCESS  read-only
        STATUS 	mandatory
        DESCRIPTION
        "This value indicates an index of a specific RFU"
        ::= { genEquipPmRfuCommonSL15minEntry 1 }

genEquipPmRfuCommonSL15minIfIndex OBJECT-TYPE
		SYNTAX  INTEGER
		ACCESS  read-only
		STATUS 	mandatory
		DESCRIPTION
		"This value indicates the interface index of a specific RFU (as appears in the ifTable)"
		::= { genEquipPmRfuCommonSL15minEntry 2 }

genEquipPmRfuCommonSL15minTimeAndDate	OBJECT-TYPE
		SYNTAX		DisplayString
        ACCESS  	read-only
        STATUS 		mandatory
        DESCRIPTION
		"This value indicates the Time and date for the specific PM."
		::= { genEquipPmRfuCommonSL15minEntry 3 }

genEquipPmRfuCommonSL15minMinRsl	OBJECT-TYPE
        SYNTAX		INTEGER
        ACCESS  	read-only
        STATUS 		mandatory
        DESCRIPTION
		"This value indicates the minimum RSL value."
		::= { genEquipPmRfuCommonSL15minEntry 4 }

genEquipPmRfuCommonSL15minMaxRsl		OBJECT-TYPE
		SYNTAX 		INTEGER
		ACCESS		read-only
        STATUS		mandatory
        DESCRIPTION
		"This value indicates the maximum RSL value."
		::= { genEquipPmRfuCommonSL15minEntry 5 }

genEquipPmRfuCommonSL15minRslExceed1		OBJECT-TYPE
		SYNTAX 		INTEGER
		ACCESS		read-only
        STATUS		mandatory
        DESCRIPTION
		"This value indicates the number of seconds RSL exceeded threshold number 1."
		::= { genEquipPmRfuCommonSL15minEntry 6 }

genEquipPmRfuCommonSL15minRslExceed2  OBJECT-TYPE
        SYNTAX  INTEGER
        ACCESS  read-only
        STATUS mandatory
        DESCRIPTION
		"This value indicates the number of seconds RSL exceeded threshold number 2."
        ::= { genEquipPmRfuCommonSL15minEntry 7 }

genEquipPmRfuCommonSL15minMinTsl  OBJECT-TYPE
		SYNTAX  INTEGER
        ACCESS  read-only
        STATUS mandatory
        DESCRIPTION
		"This value indicates the Min TSL value."
        ::= { genEquipPmRfuCommonSL15minEntry 8 }

genEquipPmRfuCommonSL15minMaxTsl  OBJECT-TYPE
		SYNTAX  INTEGER
        ACCESS  read-only
        STATUS mandatory
        DESCRIPTION
		"This value indicates the Max TSL value."
        ::= { genEquipPmRfuCommonSL15minEntry 9 }
        
genEquipPmRfuCommonSL15minTslExceed  OBJECT-TYPE
		SYNTAX  INTEGER
        ACCESS  read-only
        STATUS mandatory
        DESCRIPTION
		"This value indicates the number of seconds TSL exceeded the threshold"
        ::= { genEquipPmRfuCommonSL15minEntry 10 }
        
genEquipPmRfuCommonSL15minIDF  OBJECT-TYPE
		SYNTAX  Integrity
        ACCESS  read-only
        STATUS mandatory
        DESCRIPTION
		"This value indicates the IDF (Invalid Data Flag) of the interval.
		 integrity(0), nointegrity(1)."
        ::= { genEquipPmRfuCommonSL15minEntry 11 }
        
        
-- SL 15 min CURRENT table --

genEquipPmRfuCommonSL15minCurrTable  OBJECT-TYPE
        SYNTAX  SEQUENCE OF GenEquipPmRfuCommonSL15minCurrEntry
        ACCESS  not-accessible
        STATUS mandatory
       DESCRIPTION
        "This table indicates the RFU Signal Level PM data for the current 15 min. interval."
        ::= { genEquipPmRfuCommon 2 }

genEquipPmRfuCommonSL15minCurrEntry OBJECT-TYPE
        SYNTAX GenEquipPmRfuCommonSL15minCurrEntry
        ACCESS  not-accessible
        STATUS mandatory
        DESCRIPTION
        "Entry containing the data of the Rfu SL PM."
        INDEX { genEquipPmRfuCommonSL15minCurrId }
        ::= { genEquipPmRfuCommonSL15minCurrTable 1 }

GenEquipPmRfuCommonSL15minCurrEntry ::=
            SEQUENCE {
		genEquipPmRfuCommonSL15minCurrId			INTEGER,
		genEquipPmRfuCommonSL15minCurrIfIndex		INTEGER,
        genEquipPmRfuCommonSL15minCurrTimeAndDate	DisplayString,
        genEquipPmRfuCommonSL15minCurrMinRsl		INTEGER,
        genEquipPmRfuCommonSL15minCurrMaxRsl		INTEGER,
        genEquipPmRfuCommonSL15minCurrRslExceed1	INTEGER,
        genEquipPmRfuCommonSL15minCurrRslExceed2	INTEGER,
        genEquipPmRfuCommonSL15minCurrMinTsl		INTEGER,
        genEquipPmRfuCommonSL15minCurrMaxTsl		INTEGER,
        genEquipPmRfuCommonSL15minCurrTslExceed		INTEGER,
        genEquipPmRfuCommonSL15minCurrIDF			Integrity
	}

genEquipPmRfuCommonSL15minCurrId OBJECT-TYPE
        SYNTAX  INTEGER
        ACCESS  read-only
        STATUS 	mandatory
        DESCRIPTION
        "This value indicates an index of a specific RFU"
        ::= { genEquipPmRfuCommonSL15minCurrEntry 1 }

genEquipPmRfuCommonSL15minCurrIfIndex OBJECT-TYPE
		SYNTAX  INTEGER
		ACCESS  read-only
		STATUS 	mandatory
		DESCRIPTION
		"This value indicates the interface index of a specific RFU (as appears in the ifTable)"
		::= { genEquipPmRfuCommonSL15minCurrEntry 2 }

genEquipPmRfuCommonSL15minCurrTimeAndDate	OBJECT-TYPE
		SYNTAX		DisplayString
        ACCESS  	read-only
        STATUS 		mandatory
        DESCRIPTION
		"This value indicates the Time and date for the specific PM."
		::= { genEquipPmRfuCommonSL15minCurrEntry 3 }

genEquipPmRfuCommonSL15minCurrMinRsl	OBJECT-TYPE
        SYNTAX		INTEGER
        ACCESS  	read-only
        STATUS 		mandatory
        DESCRIPTION
		"This value indicates the minimum RSL value."
		::= { genEquipPmRfuCommonSL15minCurrEntry 4 }

genEquipPmRfuCommonSL15minCurrMaxRsl		OBJECT-TYPE
		SYNTAX 		INTEGER
		ACCESS		read-only
        STATUS		mandatory
        DESCRIPTION
		"This value indicates the maximum RSL value."
		::= { genEquipPmRfuCommonSL15minCurrEntry 5 }

genEquipPmRfuCommonSL15minCurrRslExceed1		OBJECT-TYPE
		SYNTAX 		INTEGER
		ACCESS		read-only
        STATUS		mandatory
        DESCRIPTION
		"This value indicates the number of seconds RSL exceeded threshold number 1."
		::= { genEquipPmRfuCommonSL15minCurrEntry 6 }

genEquipPmRfuCommonSL15minCurrRslExceed2  OBJECT-TYPE
        SYNTAX  INTEGER
        ACCESS  read-only
        STATUS mandatory
        DESCRIPTION
		"This value indicates the number of seconds RSL exceeded threshold number 2."
        ::= { genEquipPmRfuCommonSL15minCurrEntry 7 }

genEquipPmRfuCommonSL15minCurrMinTsl  OBJECT-TYPE
		SYNTAX  INTEGER
        ACCESS  read-only
        STATUS mandatory
        DESCRIPTION
		"This value indicates the Min TSL value."
        ::= { genEquipPmRfuCommonSL15minCurrEntry 8 }

genEquipPmRfuCommonSL15minCurrMaxTsl  OBJECT-TYPE
		SYNTAX  INTEGER
        ACCESS  read-only
        STATUS mandatory
        DESCRIPTION
		"This value indicates the Max TSL value."
        ::= { genEquipPmRfuCommonSL15minCurrEntry 9 }
        
genEquipPmRfuCommonSL15minCurrTslExceed  OBJECT-TYPE
		SYNTAX  INTEGER
        ACCESS  read-only
        STATUS mandatory
        DESCRIPTION
		"This value indicates the number of seconds TSL exceeded the threshold"
        ::= { genEquipPmRfuCommonSL15minCurrEntry 10 }
        
genEquipPmRfuCommonSL15minCurrIDF  OBJECT-TYPE
		SYNTAX  Integrity
        ACCESS  read-only
        STATUS mandatory
        DESCRIPTION
		"This value indicates the IDF (Invalid Data Flag) of the current interval.
		 integrity(0), nointegrity(1)."
        ::= { genEquipPmRfuCommonSL15minCurrEntry 11 }
        
-- PM Tables for SL 24 hour intervals

genEquipPmRfuCommonSL24hrTable  OBJECT-TYPE
        SYNTAX  SEQUENCE OF GenEquipPmRfuCommonSL24hrEntry
        ACCESS  not-accessible
        STATUS mandatory
        DESCRIPTION
        "This table indicates the RFU Signal Level 24 hr PM data."
        ::= { genEquipPmRfuCommon 3 }

genEquipPmRfuCommonSL24hrEntry OBJECT-TYPE
        SYNTAX GenEquipPmRfuCommonSL24hrEntry
        ACCESS  not-accessible
        STATUS mandatory
        DESCRIPTION
        "Entry containing the data of the RFU SL PM."
        INDEX { genEquipPmRfuCommonSL24hrId }
        ::= { genEquipPmRfuCommonSL24hrTable 1 }

GenEquipPmRfuCommonSL24hrEntry ::=
            SEQUENCE {
		genEquipPmRfuCommonSL24hrId				INTEGER,
		genEquipPmRfuCommonSL24hrIfIndex		INTEGER,
        genEquipPmRfuCommonSL24hrTimeAndDate	DisplayString,
        genEquipPmRfuCommonSL24hrMinRsl			INTEGER,
        genEquipPmRfuCommonSL24hrMaxRsl			INTEGER,
        genEquipPmRfuCommonSL24hrRslExceed1		INTEGER,
        genEquipPmRfuCommonSL24hrRslExceed2		INTEGER,
        genEquipPmRfuCommonSL24hrMinTsl			INTEGER,
        genEquipPmRfuCommonSL24hrMaxTsl			INTEGER,
        genEquipPmRfuCommonSL24hrTslExceed		INTEGER,
        genEquipPmRfuCommonSL24hrIDF			Integrity
	}

genEquipPmRfuCommonSL24hrId OBJECT-TYPE
        SYNTAX  INTEGER
        ACCESS  read-only
        STATUS 	mandatory
        DESCRIPTION
        "This value indicates an index of a specific RFU"
        ::= { genEquipPmRfuCommonSL24hrEntry 1 }

genEquipPmRfuCommonSL24hrIfIndex OBJECT-TYPE
		SYNTAX  INTEGER
		ACCESS  read-only
		STATUS 	mandatory
		DESCRIPTION
		"This value indicates the interface index of a specific RFU (as appears in the ifTable)"
		::= { genEquipPmRfuCommonSL24hrEntry 2 }

genEquipPmRfuCommonSL24hrTimeAndDate	OBJECT-TYPE
		SYNTAX		DisplayString
        ACCESS  	read-only
        STATUS 		mandatory
        DESCRIPTION
		"This value indicates the time and date for the specific PM."
		::= { genEquipPmRfuCommonSL24hrEntry 3 }

genEquipPmRfuCommonSL24hrMinRsl	OBJECT-TYPE
        SYNTAX		INTEGER
        ACCESS  	read-only
        STATUS 		mandatory
        DESCRIPTION
		"This value indicates the min RSL value."
		::= { genEquipPmRfuCommonSL24hrEntry 4 }

genEquipPmRfuCommonSL24hrMaxRsl		OBJECT-TYPE
		SYNTAX 		INTEGER
		ACCESS		read-only
        STATUS		mandatory
        DESCRIPTION
		"This value indicates the max RSL value."
		::= { genEquipPmRfuCommonSL24hrEntry 5 }

genEquipPmRfuCommonSL24hrRslExceed1		OBJECT-TYPE
		SYNTAX 		INTEGER
		ACCESS		read-only
        STATUS		mandatory
        DESCRIPTION
		"This value indicates the number of seconds RSL exceeded threshold number 1."
		::= { genEquipPmRfuCommonSL24hrEntry 6 }

genEquipPmRfuCommonSL24hrRslExceed2  OBJECT-TYPE
        SYNTAX  INTEGER
        ACCESS  read-only
        STATUS mandatory
        DESCRIPTION
		"This value indicates the number of seconds RSL exceeded threshold number 2."
        ::= { genEquipPmRfuCommonSL24hrEntry 7 }

genEquipPmRfuCommonSL24hrMinTsl  OBJECT-TYPE
		SYNTAX  INTEGER
        ACCESS  read-only
        STATUS mandatory
        DESCRIPTION
		"This value indicates the Min TSL value."
        ::= { genEquipPmRfuCommonSL24hrEntry 8 }

genEquipPmRfuCommonSL24hrMaxTsl  OBJECT-TYPE
		SYNTAX  INTEGER
        ACCESS  read-only
        STATUS mandatory
        DESCRIPTION
		"This value indicates the Max TSL value."
        ::= { genEquipPmRfuCommonSL24hrEntry 9 }
        
genEquipPmRfuCommonSL24hrTslExceed  OBJECT-TYPE
		SYNTAX  INTEGER
        ACCESS  read-only
        STATUS mandatory
        DESCRIPTION
		"This value indicates the number of seconds RSL exceeded the threshold"
        ::= { genEquipPmRfuCommonSL24hrEntry 10 }
        
genEquipPmRfuCommonSL24hrIDF  OBJECT-TYPE
		SYNTAX  Integrity
        ACCESS  read-only
        STATUS mandatory
        DESCRIPTION
		"This value indicates the IDF (Invalid Data Flag) of the interval.
		 integrity(0), nointegrity(1)."
        ::= { genEquipPmRfuCommonSL24hrEntry 11 }
        
        
-- SL 24 HR CURRENT table --

genEquipPmRfuCommonSL24hrCurrTable  OBJECT-TYPE
        SYNTAX  SEQUENCE OF GenEquipPmRfuCommonSL24hrCurrEntry
        ACCESS  not-accessible
        STATUS mandatory
       DESCRIPTION
        "This table indicates the RFU Signal Level PM data for the current 24 hour interval."
        ::= { genEquipPmRfuCommon 4 }

genEquipPmRfuCommonSL24hrCurrEntry OBJECT-TYPE
        SYNTAX GenEquipPmRfuCommonSL24hrCurrEntry
        ACCESS  not-accessible
        STATUS mandatory
        DESCRIPTION
        "Entry containing the data of the RFU SL PM."
        INDEX { genEquipPmRfuCommonSL24hrCurrId }
        ::= { genEquipPmRfuCommonSL24hrCurrTable 1 }

GenEquipPmRfuCommonSL24hrCurrEntry ::=
            SEQUENCE {
		genEquipPmRfuCommonSL24hrCurrId				INTEGER,
		genEquipPmRfuCommonSL24hrCurrIfIndex		INTEGER,
        genEquipPmRfuCommonSL24hrCurrTimeAndDate	DisplayString,
        genEquipPmRfuCommonSL24hrCurrMinRsl			INTEGER,
        genEquipPmRfuCommonSL24hrCurrMaxRsl			INTEGER,
        genEquipPmRfuCommonSL24hrCurrRslExceed1		INTEGER,
        genEquipPmRfuCommonSL24hrCurrRslExceed2		INTEGER,
        genEquipPmRfuCommonSL24hrCurrMinTsl			INTEGER,
        genEquipPmRfuCommonSL24hrCurrMaxTsl			INTEGER,
        genEquipPmRfuCommonSL24hrCurrTslExceed		INTEGER,
        genEquipPmRfuCommonSL24hrCurrIDF			Integrity
	}

genEquipPmRfuCommonSL24hrCurrId OBJECT-TYPE
        SYNTAX  INTEGER
        ACCESS  read-only
        STATUS 	mandatory
        DESCRIPTION
        "This value indicates an index of a specific RFU"
        ::= { genEquipPmRfuCommonSL24hrCurrEntry 1 }

genEquipPmRfuCommonSL24hrCurrIfIndex OBJECT-TYPE
		SYNTAX  INTEGER
		ACCESS  read-only
		STATUS 	mandatory
		DESCRIPTION
		"This value indicates the interface index of a specific RFU (as appears in the ifTable)"
		::= { genEquipPmRfuCommonSL24hrCurrEntry 2 }

genEquipPmRfuCommonSL24hrCurrTimeAndDate	OBJECT-TYPE
		SYNTAX		DisplayString
        ACCESS  	read-only
        STATUS 		mandatory
        DESCRIPTION
		"This value indicates the time and date for the specific PM."
		::= { genEquipPmRfuCommonSL24hrCurrEntry 3 }

genEquipPmRfuCommonSL24hrCurrMinRsl	OBJECT-TYPE
        SYNTAX		INTEGER
        ACCESS  	read-only
        STATUS 		mandatory
        DESCRIPTION
		"This value indicates the min RSL value."
		::= { genEquipPmRfuCommonSL24hrCurrEntry 4 }

genEquipPmRfuCommonSL24hrCurrMaxRsl		OBJECT-TYPE
		SYNTAX 		INTEGER
		ACCESS		read-only
        STATUS		mandatory
        DESCRIPTION
		"This value indicates the Max RSL value."
		::= { genEquipPmRfuCommonSL24hrCurrEntry 5 }

genEquipPmRfuCommonSL24hrCurrRslExceed1		OBJECT-TYPE
		SYNTAX 		INTEGER
		ACCESS		read-only
        STATUS		mandatory
        DESCRIPTION
		"This value indicates the number of seconds RSL exceeded threshold number 1."
		::= { genEquipPmRfuCommonSL24hrCurrEntry 6 }

genEquipPmRfuCommonSL24hrCurrRslExceed2  OBJECT-TYPE
        SYNTAX  INTEGER
        ACCESS  read-only
        STATUS mandatory
        DESCRIPTION
		"This value indicates the number of seconds RSL exceeded threshold number 2."
        ::= { genEquipPmRfuCommonSL24hrCurrEntry 7 }

genEquipPmRfuCommonSL24hrCurrMinTsl  OBJECT-TYPE
		SYNTAX  INTEGER
        ACCESS  read-only
        STATUS mandatory
        DESCRIPTION
		"This value indicates the Min TSL value."
        ::= { genEquipPmRfuCommonSL24hrCurrEntry 8 }

genEquipPmRfuCommonSL24hrCurrMaxTsl  OBJECT-TYPE
		SYNTAX  INTEGER
        ACCESS  read-only
        STATUS mandatory
        DESCRIPTION
		"This value indicates the Max TSL value."
        ::= { genEquipPmRfuCommonSL24hrCurrEntry 9 }
        
genEquipPmRfuCommonSL24hrCurrTslExceed  OBJECT-TYPE
		SYNTAX  INTEGER
        ACCESS  read-only
        STATUS mandatory
        DESCRIPTION
		"This value indicates the number of seconds TSL exceeded the threshold"
        ::= { genEquipPmRfuCommonSL24hrCurrEntry 10 }
        
genEquipPmRfuCommonSL24hrCurrIDF  OBJECT-TYPE
		SYNTAX  Integrity
        ACCESS  read-only
        STATUS mandatory
        DESCRIPTION
		"This value indicates the IDF (Invalid Data Flag) of the interval.
		 integrity(0), nointegrity(1)."
        ::= { genEquipPmRfuCommonSL24hrCurrEntry 11 }
        

        
--	PM for Radio Aggregate - 15 min intervals

genEquipPmTraffic	OBJECT IDENTIFIER ::= {genEquipPM 2}

genEquipPmTrafficRadioAgg15minTable  OBJECT-TYPE
        SYNTAX  SEQUENCE OF GenEquipPmTrafficRadioAgg15minEntry
        ACCESS  not-accessible
        STATUS mandatory
       DESCRIPTION
        "This table indicates the Radio Aggregate PM data for all 15 min intervals."
        ::= { genEquipPmTraffic 1 }

genEquipPmTrafficRadioAgg15minEntry OBJECT-TYPE
        SYNTAX GenEquipPmTrafficRadioAgg15minEntry
        ACCESS  not-accessible
        STATUS mandatory
        DESCRIPTION
        "This table indicates the Radio Aggregate PM data for all 15 min intervals."
        INDEX { genEquipPmTrafficRadioAgg15minId }
        ::= { genEquipPmTrafficRadioAgg15minTable 1 }

GenEquipPmTrafficRadioAgg15minEntry ::=
            SEQUENCE {
		genEquipPmTrafficRadioAgg15minId				INTEGER,
		genEquipPmTrafficRadioAgg15minIfIndex		INTEGER,
        genEquipPmTrafficRadioAgg15minTimeAndDate	DisplayString,
        genEquipPmTrafficRadioAgg15minES				INTEGER,
        genEquipPmTrafficRadioAgg15minSES			INTEGER,
        genEquipPmTrafficRadioAgg15minUAS			INTEGER,
        genEquipPmTrafficRadioAgg15minBBE			INTEGER,
        genEquipPmTrafficRadioAgg15minIDF			Integrity
	}

genEquipPmTrafficRadioAgg15minId OBJECT-TYPE
        SYNTAX  INTEGER
        ACCESS  read-only
        STATUS 	mandatory
        DESCRIPTION
        "This value indicates an index of a specific RFU"
        ::= { genEquipPmTrafficRadioAgg15minEntry 1 }

genEquipPmTrafficRadioAgg15minIfIndex OBJECT-TYPE
		SYNTAX  INTEGER
		ACCESS  read-only
		STATUS 	mandatory
		DESCRIPTION
		"This value indicates the interface index of a specific RFU (as appears in the ifTable)"
		::= { genEquipPmTrafficRadioAgg15minEntry 2 }

genEquipPmTrafficRadioAgg15minTimeAndDate	OBJECT-TYPE
		SYNTAX		DisplayString
        ACCESS  	read-only
        STATUS 		mandatory
        DESCRIPTION
		"This value indicates the time and date for the specific PM."
		::= { genEquipPmTrafficRadioAgg15minEntry 3 }

genEquipPmTrafficRadioAgg15minES	OBJECT-TYPE
        SYNTAX		INTEGER
        ACCESS  	read-only
        STATUS 		mandatory
        DESCRIPTION
		"This value indicates the ES value."
		::= { genEquipPmTrafficRadioAgg15minEntry 4 }

genEquipPmTrafficRadioAgg15minSES		OBJECT-TYPE
		SYNTAX 		INTEGER
		ACCESS		read-only
        STATUS		mandatory
        DESCRIPTION
		"This value indicates the SES value."
		::= { genEquipPmTrafficRadioAgg15minEntry 5 }

genEquipPmTrafficRadioAgg15minUAS		OBJECT-TYPE
		SYNTAX 		INTEGER
		ACCESS		read-only
        STATUS		mandatory
        DESCRIPTION
		"This value indicates the UAS value."
		::= { genEquipPmTrafficRadioAgg15minEntry 6 }

genEquipPmTrafficRadioAgg15minBBE  OBJECT-TYPE
        SYNTAX  INTEGER
        ACCESS  read-only
        STATUS mandatory
        DESCRIPTION
		"This value indicates the BBE value."
        ::= { genEquipPmTrafficRadioAgg15minEntry 7 }

     
genEquipPmTrafficRadioAgg15minIDF  OBJECT-TYPE
		SYNTAX  Integrity
        ACCESS  read-only
        STATUS mandatory
        DESCRIPTION
		"This value indicates the IDF (Invalid Data Flag) of the interval.
		 integrity(0), nointegrity(1)."
        ::= { genEquipPmTrafficRadioAgg15minEntry 8 }

-- PM for Radio Agg. - 15min - Current interval

genEquipPmTrafficRadioAgg15minCurrTable  OBJECT-TYPE
        SYNTAX  SEQUENCE OF GenEquipPmTrafficRadioAgg15minCurrEntry
        ACCESS  not-accessible
        STATUS mandatory
       DESCRIPTION
        "This table indicates the Radio Aggregate PM data for all 15 min intervals."
        ::= { genEquipPmTraffic 2 }

genEquipPmTrafficRadioAgg15minCurrEntry OBJECT-TYPE
        SYNTAX GenEquipPmTrafficRadioAgg15minCurrEntry
        ACCESS  not-accessible
        STATUS mandatory
        DESCRIPTION
        "This table indicates the Radio Aggregate PM data for all 15 min intervals."
        INDEX { genEquipPmTrafficRadioAgg15minCurrId }
        ::= { genEquipPmTrafficRadioAgg15minCurrTable 1 }

GenEquipPmTrafficRadioAgg15minCurrEntry ::=
            SEQUENCE {
		genEquipPmTrafficRadioAgg15minCurrId				INTEGER,
		genEquipPmTrafficRadioAgg15minCurrIfIndex		INTEGER,
        genEquipPmTrafficRadioAgg15minCurrTimeAndDate	DisplayString,
        genEquipPmTrafficRadioAgg15minCurrES				INTEGER,
        genEquipPmTrafficRadioAgg15minCurrSES			INTEGER,
        genEquipPmTrafficRadioAgg15minCurrUAS			INTEGER,
        genEquipPmTrafficRadioAgg15minCurrBBE			INTEGER,
        genEquipPmTrafficRadioAgg15minCurrIDF			Integrity
	}

genEquipPmTrafficRadioAgg15minCurrId OBJECT-TYPE
        SYNTAX  INTEGER
        ACCESS  read-only
        STATUS 	mandatory
        DESCRIPTION
        "This value indicates an index of a specific RFU"
        ::= { genEquipPmTrafficRadioAgg15minCurrEntry 1 }

genEquipPmTrafficRadioAgg15minCurrIfIndex OBJECT-TYPE
		SYNTAX  INTEGER
		ACCESS  read-only
		STATUS 	mandatory
		DESCRIPTION
		"This value indicates the interface index of a specific RFU (as appears in the ifTable)"
		::= { genEquipPmTrafficRadioAgg15minCurrEntry 2 }

genEquipPmTrafficRadioAgg15minCurrTimeAndDate	OBJECT-TYPE
		SYNTAX		DisplayString
        ACCESS  	read-only
        STATUS 		mandatory
        DESCRIPTION
		"This value indicates the time and date for the specific PM."
		::= { genEquipPmTrafficRadioAgg15minCurrEntry 3 }

genEquipPmTrafficRadioAgg15minCurrES	OBJECT-TYPE
        SYNTAX		INTEGER
        ACCESS  	read-only
        STATUS 		mandatory
        DESCRIPTION
		"This value indicates the ES value."
		::= { genEquipPmTrafficRadioAgg15minCurrEntry 4 }

genEquipPmTrafficRadioAgg15minCurrSES		OBJECT-TYPE
		SYNTAX 		INTEGER
		ACCESS		read-only
        STATUS		mandatory
        DESCRIPTION
		"This value indicates the SES value."
		::= { genEquipPmTrafficRadioAgg15minCurrEntry 5 }

genEquipPmTrafficRadioAgg15minCurrUAS		OBJECT-TYPE
		SYNTAX 		INTEGER
		ACCESS		read-only
        STATUS		mandatory
        DESCRIPTION
		"This value indicates the UAS value."
		::= { genEquipPmTrafficRadioAgg15minCurrEntry 6 }

genEquipPmTrafficRadioAgg15minCurrBBE  OBJECT-TYPE
        SYNTAX  INTEGER
        ACCESS  read-only
        STATUS mandatory
        DESCRIPTION
		"This value indicates the BBE value."
        ::= { genEquipPmTrafficRadioAgg15minCurrEntry 7 }

     
genEquipPmTrafficRadioAgg15minCurrIDF  OBJECT-TYPE
		SYNTAX  Integrity
        ACCESS  read-only
        STATUS mandatory
        DESCRIPTION
		"This value indicates the IDF (Invalid Data Flag) of the interval.
		 integrity(0), nointegrity(1)."
        ::= { genEquipPmTrafficRadioAgg15minCurrEntry 8 }
        
-- PM for Radio Aggregate - 24 hours intervals

genEquipPmTrafficRadioAgg24hrTable  OBJECT-TYPE
        SYNTAX  SEQUENCE OF GenEquipPmTrafficRadioAgg24hrEntry
        ACCESS  not-accessible
        STATUS mandatory
       DESCRIPTION
        "This table indicates the Radio Aggregate PM data for all 15 min intervals."
        ::= { genEquipPmTraffic 3 }

genEquipPmTrafficRadioAgg24hrEntry OBJECT-TYPE
        SYNTAX GenEquipPmTrafficRadioAgg24hrEntry
        ACCESS  not-accessible
        STATUS mandatory
        DESCRIPTION
        "This table indicates the Radio Aggregate PM data for all 15 min intervals."
        INDEX { genEquipPmTrafficRadioAgg24hrId }
        ::= { genEquipPmTrafficRadioAgg24hrTable 1 }

GenEquipPmTrafficRadioAgg24hrEntry ::=
            SEQUENCE {
		genEquipPmTrafficRadioAgg24hrId			INTEGER,
		genEquipPmTrafficRadioAgg24hrIfIndex		INTEGER,
        genEquipPmTrafficRadioAgg24hrTimeAndDate	DisplayString,
        genEquipPmTrafficRadioAgg24hrES			INTEGER,
        genEquipPmTrafficRadioAgg24hrSES			INTEGER,
        genEquipPmTrafficRadioAgg24hrUAS			INTEGER,
        genEquipPmTrafficRadioAgg24hrBBE			INTEGER,
        genEquipPmTrafficRadioAgg24hrIDF			Integrity
	}

genEquipPmTrafficRadioAgg24hrId OBJECT-TYPE
        SYNTAX  INTEGER
        ACCESS  read-only
        STATUS 	mandatory
        DESCRIPTION
        "This value indicates an index of a specific RFU"
        ::= { genEquipPmTrafficRadioAgg24hrEntry 1 }

genEquipPmTrafficRadioAgg24hrIfIndex OBJECT-TYPE
		SYNTAX  INTEGER
		ACCESS  read-only
		STATUS 	mandatory
		DESCRIPTION
		"This value indicates the interface index of a specific RFU (as appears in the ifTable)"
		::= { genEquipPmTrafficRadioAgg24hrEntry 2 }

genEquipPmTrafficRadioAgg24hrTimeAndDate	OBJECT-TYPE
		SYNTAX		DisplayString
        ACCESS  	read-only
        STATUS 		mandatory
        DESCRIPTION
		"This value indicates the time and date for the specific PM."
		::= { genEquipPmTrafficRadioAgg24hrEntry 3 }

genEquipPmTrafficRadioAgg24hrES	OBJECT-TYPE
        SYNTAX		INTEGER
        ACCESS  	read-only
        STATUS 		mandatory
        DESCRIPTION
		"This value indicates the ES value."
		::= { genEquipPmTrafficRadioAgg24hrEntry 4 }

genEquipPmTrafficRadioAgg24hrSES		OBJECT-TYPE
		SYNTAX 		INTEGER
		ACCESS		read-only
        STATUS		mandatory
        DESCRIPTION
		"This value indicates the SES value."
		::= { genEquipPmTrafficRadioAgg24hrEntry 5 }

genEquipPmTrafficRadioAgg24hrUAS		OBJECT-TYPE
		SYNTAX 		INTEGER
		ACCESS		read-only
        STATUS		mandatory
        DESCRIPTION
		"This value indicates the UAS value."
		::= { genEquipPmTrafficRadioAgg24hrEntry 6 }

genEquipPmTrafficRadioAgg24hrBBE  OBJECT-TYPE
        SYNTAX  INTEGER
        ACCESS  read-only
        STATUS mandatory
        DESCRIPTION
		"This value indicates the BBE value."
        ::= { genEquipPmTrafficRadioAgg24hrEntry 7 }

     
genEquipPmTrafficRadioAgg24hrIDF  OBJECT-TYPE
		SYNTAX  Integrity
        ACCESS  read-only
        STATUS mandatory
        DESCRIPTION
		"This value indicates the IDF (Invalid Data Flag) of the interval.
		 integrity(0), nointegrity(1)."
        ::= { genEquipPmTrafficRadioAgg24hrEntry 8 }

-- PM for Radio Agg. - 24hr - Current interval

genEquipPmTrafficRadioAgg24hrCurrTable  OBJECT-TYPE
        SYNTAX  SEQUENCE OF GenEquipPmTrafficRadioAgg24hrCurrEntry
        ACCESS  not-accessible
        STATUS mandatory
       DESCRIPTION
        "This table indicates the Radio Aggregate PM data for all 15 min intervals."
        ::= { genEquipPmTraffic 4 }

genEquipPmTrafficRadioAgg24hrCurrEntry OBJECT-TYPE
        SYNTAX GenEquipPmTrafficRadioAgg24hrCurrEntry
        ACCESS  not-accessible
        STATUS mandatory
        DESCRIPTION
        "This table indicates the Radio Aggregate PM data for all 15 min intervals."
        INDEX { genEquipPmTrafficRadioAgg24hrCurrId }
        ::= { genEquipPmTrafficRadioAgg24hrCurrTable 1 }

GenEquipPmTrafficRadioAgg24hrCurrEntry ::=
            SEQUENCE {
		genEquipPmTrafficRadioAgg24hrCurrId			INTEGER,
		genEquipPmTrafficRadioAgg24hrCurrIfIndex		INTEGER,
        genEquipPmTrafficRadioAgg24hrCurrTimeAndDate	DisplayString,
        genEquipPmTrafficRadioAgg24hrCurrES			INTEGER,
        genEquipPmTrafficRadioAgg24hrCurrSES			INTEGER,
        genEquipPmTrafficRadioAgg24hrCurrUAS			INTEGER,
        genEquipPmTrafficRadioAgg24hrCurrBBE			INTEGER,
        genEquipPmTrafficRadioAgg24hrCurrIDF			Integrity
	}

genEquipPmTrafficRadioAgg24hrCurrId OBJECT-TYPE
        SYNTAX  INTEGER
        ACCESS  read-only
        STATUS 	mandatory
        DESCRIPTION
        "This value indicates an index of a specific RFU"
        ::= { genEquipPmTrafficRadioAgg24hrCurrEntry 1 }

genEquipPmTrafficRadioAgg24hrCurrIfIndex OBJECT-TYPE
		SYNTAX  INTEGER
		ACCESS  read-only
		STATUS 	mandatory
		DESCRIPTION
		"This value indicates the interface index of a specific RFU (as appears in the ifTable)"
		::= { genEquipPmTrafficRadioAgg24hrCurrEntry 2 }

genEquipPmTrafficRadioAgg24hrCurrTimeAndDate	OBJECT-TYPE
		SYNTAX		DisplayString
        ACCESS  	read-only
        STATUS 		mandatory
        DESCRIPTION
		"This value indicates the time and date for the specific PM."
		::= { genEquipPmTrafficRadioAgg24hrCurrEntry 3 }

genEquipPmTrafficRadioAgg24hrCurrES	OBJECT-TYPE
        SYNTAX		INTEGER
        ACCESS  	read-only
        STATUS 		mandatory
        DESCRIPTION
		"This value indicates the ES value."
		::= { genEquipPmTrafficRadioAgg24hrCurrEntry 4 }

genEquipPmTrafficRadioAgg24hrCurrSES		OBJECT-TYPE
		SYNTAX 		INTEGER
		ACCESS		read-only
        STATUS		mandatory
        DESCRIPTION
		"This value indicates the SES value."
		::= { genEquipPmTrafficRadioAgg24hrCurrEntry 5 }

genEquipPmTrafficRadioAgg24hrCurrUAS		OBJECT-TYPE
		SYNTAX 		INTEGER
		ACCESS		read-only
        STATUS		mandatory
        DESCRIPTION
		"This value indicates the UAS value."
		::= { genEquipPmTrafficRadioAgg24hrCurrEntry 6 }

genEquipPmTrafficRadioAgg24hrCurrBBE  OBJECT-TYPE
        SYNTAX  INTEGER
        ACCESS  read-only
        STATUS mandatory
        DESCRIPTION
		"This value indicates the BBE value."
        ::= { genEquipPmTrafficRadioAgg24hrCurrEntry 7 }

     
genEquipPmTrafficRadioAgg24hrCurrIDF  OBJECT-TYPE
		SYNTAX  Integrity
        ACCESS  read-only
        STATUS mandatory
        DESCRIPTION
		"This value indicates the IDF (Invalid Data Flag) of the current interval.
		 integrity(0), nointegrity(1)."
        ::= { genEquipPmTrafficRadioAgg24hrCurrEntry 8 }




-- 	New PM tables - Add PM Table Type to the tables as index.	
genEquipPmAll	OBJECT IDENTIFIER ::= {genEquipPM 3}

genEquipPmClear  OBJECT-TYPE
		SYNTAX  OffOn
        ACCESS  read-write
        STATUS mandatory
        DESCRIPTION
		"Clear All values for PM tables."
        ::= { genEquipPmAll 1 }
		

-- 	Signal Level PM Group	
genEquipPmTrafficSL	OBJECT IDENTIFIER ::= {genEquipPmAll 2}
		
genEquipPmTrafficSLTable  OBJECT-TYPE
        SYNTAX  SEQUENCE OF GenEquipPmTrafficSLEntry
        ACCESS  not-accessible
        STATUS mandatory
        DESCRIPTION
        "This table indicates the RFU Signal Level PM data."
        ::= { genEquipPmTrafficSL 1 }

genEquipPmTrafficSLEntry OBJECT-TYPE
        SYNTAX GenEquipPmTrafficSLEntry
        ACCESS  not-accessible
        STATUS mandatory
        DESCRIPTION
        "Entry containing the data of the RFU signal level PM."
        INDEX { genEquipPmTrafficSLPmType, genEquipPmTrafficSLId, genEquipPmTrafficSLInterval }
        ::= { genEquipPmTrafficSLTable 1 }

GenEquipPmTrafficSLEntry ::=
            SEQUENCE {
		genEquipPmTrafficSLPmType		PmTableType,
		genEquipPmTrafficSLId			RfuId,
		genEquipPmTrafficSLInterval		INTEGER,
        genEquipPmTrafficSLMinRsl		INTEGER,
        genEquipPmTrafficSLMaxRsl		INTEGER,
        genEquipPmTrafficSLRslExceed1	INTEGER,
        genEquipPmTrafficSLRslExceed2	INTEGER,
        genEquipPmTrafficSLMinTsl		INTEGER,
        genEquipPmTrafficSLMaxTsl		INTEGER,
        genEquipPmTrafficSLTslExceed	INTEGER,
        genEquipPmTrafficSLIDF			Integrity
	}

genEquipPmTrafficSLPmType OBJECT-TYPE
        SYNTAX  PmTableType
        ACCESS  read-only
        STATUS 	mandatory
        DESCRIPTION
        "This value indicates the PM Type table to access, 15 min, current 15 min, 24 hours or current 24 hours"
        ::= { genEquipPmTrafficSLEntry 1 }

genEquipPmTrafficSLId OBJECT-TYPE
        SYNTAX  RfuId
        ACCESS  read-only
        STATUS 	mandatory
        DESCRIPTION
        "This value indicates an index of a specific RFU"
        ::= { genEquipPmTrafficSLEntry 2 }

genEquipPmTrafficSLInterval OBJECT-TYPE
        SYNTAX  INTEGER
        ACCESS  read-only
        STATUS 	mandatory
        DESCRIPTION
        "This value indicates an index of a specific PM Interval"
        ::= { genEquipPmTrafficSLEntry 3 }

genEquipPmTrafficSLMinRsl	OBJECT-TYPE
        SYNTAX		INTEGER
        ACCESS  	read-only
        STATUS 		mandatory
        DESCRIPTION
		"This value indicates the min RSL value."
		::= { genEquipPmTrafficSLEntry 4 }

genEquipPmTrafficSLMaxRsl		OBJECT-TYPE
		SYNTAX 		INTEGER
		ACCESS		read-only
        STATUS		mandatory
        DESCRIPTION
		"This value indicates the max RSL value."
		::= { genEquipPmTrafficSLEntry 5 }

genEquipPmTrafficSLRslExceed1		OBJECT-TYPE
		SYNTAX 		INTEGER
		ACCESS		read-only
        STATUS		mandatory
        DESCRIPTION
		"This value indicates the number of seconds RSL exceeded threshold number 1."
		::= { genEquipPmTrafficSLEntry 6 }

genEquipPmTrafficSLRslExceed2  OBJECT-TYPE
        SYNTAX  INTEGER
        ACCESS  read-only
        STATUS mandatory
        DESCRIPTION
		"This value indicates the number of seconds RSL exceeded threshold number 2."
        ::= { genEquipPmTrafficSLEntry 7 }

genEquipPmTrafficSLMinTsl  OBJECT-TYPE
		SYNTAX  INTEGER
        ACCESS  read-only
        STATUS mandatory
        DESCRIPTION
		"This value indicates the Minimum TSL value."
        ::= { genEquipPmTrafficSLEntry 8 }

genEquipPmTrafficSLMaxTsl  OBJECT-TYPE
		SYNTAX  INTEGER
        ACCESS  read-only
        STATUS mandatory
        DESCRIPTION
		"This value indicates the Maximum TSL value."
        ::= { genEquipPmTrafficSLEntry 9 }
        
genEquipPmTrafficSLTslExceed  OBJECT-TYPE
		SYNTAX  INTEGER
        ACCESS  read-only
        STATUS mandatory
        DESCRIPTION
		"This value indicates the number of seconds TSL exceeded the threshold"
        ::= { genEquipPmTrafficSLEntry 10 }
        
genEquipPmTrafficSLIDF  OBJECT-TYPE
		SYNTAX  Integrity
        ACCESS  read-only
        STATUS mandatory
        DESCRIPTION
		"This value indicates if the IDF (Invalid Data Flag), was set."
        ::= { genEquipPmTrafficSLEntry 11 }
        
-- 	Aggregate PM Group	
genEquipPmTrafficAggregate	OBJECT IDENTIFIER ::= {genEquipPmAll 3}
		
genEquipPmTrafficAggTable  OBJECT-TYPE
        SYNTAX  SEQUENCE OF GenEquipPmTrafficAggEntry
        ACCESS  not-accessible
        STATUS mandatory
       DESCRIPTION
        "This table indicates the Radio Aggregate PM data."
        ::= { genEquipPmTrafficAggregate 1 }

genEquipPmTrafficAggEntry OBJECT-TYPE
        SYNTAX GenEquipPmTrafficAggEntry
        ACCESS  not-accessible
        STATUS mandatory
        DESCRIPTION
        "This table indicates the Radio Aggregate PM data."
        INDEX { genEquipPmTrafficAggPmType, ifIndex, genEquipPmTrafficAggInterval }
        ::= { genEquipPmTrafficAggTable 1 }

GenEquipPmTrafficAggEntry ::=
            SEQUENCE {
		genEquipPmTrafficAggPmType			PmTableType,
		genEquipPmTrafficAggInterval		INTEGER,
        genEquipPmTrafficAggES				INTEGER,
        genEquipPmTrafficAggSES				INTEGER,
        genEquipPmTrafficAggUAS				INTEGER,
        genEquipPmTrafficAggBBE				INTEGER,
        genEquipPmTrafficAggIDF				Integrity
	}

genEquipPmTrafficAggPmType OBJECT-TYPE
        SYNTAX  PmTableType
        ACCESS  read-only
        STATUS 	mandatory
        DESCRIPTION
        "This value indicates the PM Type table to access, 15 min, current 15 min, 24 hours or current 24 hours"
        ::= { genEquipPmTrafficAggEntry 1 }

genEquipPmTrafficAggInterval OBJECT-TYPE
        SYNTAX  INTEGER
        ACCESS  read-only
        STATUS 	mandatory
        DESCRIPTION
        "This value indicates an index of a specific PM Interval"
        ::= { genEquipPmTrafficAggEntry 2 }

genEquipPmTrafficAggES	OBJECT-TYPE
        SYNTAX		INTEGER
        ACCESS  	read-only
        STATUS 		mandatory
        DESCRIPTION
		"This value indicates the ES value (Errored seconds)."
		::= { genEquipPmTrafficAggEntry 3 }

genEquipPmTrafficAggSES		OBJECT-TYPE
		SYNTAX 		INTEGER
		ACCESS		read-only
        STATUS		mandatory
        DESCRIPTION
		"This value indicates the SES value (Severe Errored seconds)."
		::= { genEquipPmTrafficAggEntry 4 }

genEquipPmTrafficAggUAS		OBJECT-TYPE
		SYNTAX 		INTEGER
		ACCESS		read-only
        STATUS		mandatory
        DESCRIPTION
		"This value indicates the UAS value. (Unavailable Seconds)"
		::= { genEquipPmTrafficAggEntry 5 }

genEquipPmTrafficAggBBE  OBJECT-TYPE
        SYNTAX  INTEGER
        ACCESS  read-only
        STATUS mandatory
        DESCRIPTION
		"This value indicates the BBE value. (Background Block Error)"
        ::= { genEquipPmTrafficAggEntry 6 }

     
genEquipPmTrafficAggIDF  OBJECT-TYPE
		SYNTAX  Integrity
        ACCESS  read-only
        STATUS mandatory
        DESCRIPTION
		"This value indicates if the IDF (Invalid Data Flag), was set."
        ::= { genEquipPmTrafficAggEntry 7 }



-- 	Radio PM Group	
genEquipPmRadio	OBJECT IDENTIFIER ::= {genEquipPmAll 4}

-- 	Radio MRMC PM Group	
genEquipPmRadioMRMC	OBJECT IDENTIFIER ::= {genEquipPmRadio 1}

-- Radio MRMC PM Table
genEquipPmRadioMRMCTable  OBJECT-TYPE
        SYNTAX  SEQUENCE OF GenEquipPmRadioMRMCEntry
        ACCESS  not-accessible
        STATUS mandatory
       DESCRIPTION
        "The MRMC PM table"
        ::= { genEquipPmRadioMRMC 1 }

genEquipPmRadioMRMCEntry OBJECT-TYPE
        SYNTAX GenEquipPmRadioMRMCEntry
        ACCESS  not-accessible
        STATUS mandatory
        DESCRIPTION
        "The MRMC PM table"
        INDEX { genEquipPmRadioMRMCPmType, genEquipPmRadioMRMCId, genEquipPmRadioMRMCInterval }
        ::= { genEquipPmRadioMRMCTable 1 }

GenEquipPmRadioMRMCEntry ::=
            SEQUENCE {
		genEquipPmRadioMRMCPmType			PmTableType,
		genEquipPmRadioMRMCId				RadioId,
		genEquipPmRadioMRMCInterval			INTEGER,
		genEquipPmRadioMRMCIfIndex			INTEGER,
        genEquipPmRadioMRMCMinProfile		INTEGER,
        genEquipPmRadioMRMCMaxProfile		INTEGER,
        genEquipPmRadioMRMCMinBitrate		INTEGER,
        genEquipPmRadioMRMCMaxBitrate		INTEGER,
        genEquipPmRadioMRMCMinTDMIf			INTEGER,
        genEquipPmRadioMRMCMaxTDMIf			INTEGER,
        genEquipPmRadioMRMCIDF				Integrity
	}

genEquipPmRadioMRMCPmType OBJECT-TYPE
        SYNTAX  PmTableType
        ACCESS  read-only
        STATUS 	mandatory
        DESCRIPTION
        "This value indicates the PM Type table to access, 15 min, current 15 min, 24 hours or current 24 hours"
        ::= { genEquipPmRadioMRMCEntry 1 }

genEquipPmRadioMRMCId OBJECT-TYPE
        SYNTAX  RadioId
        ACCESS  read-only
        STATUS 	mandatory
        DESCRIPTION
        "This value indicates an index of a specific RFU"
        ::= { genEquipPmRadioMRMCEntry 2 }

genEquipPmRadioMRMCInterval OBJECT-TYPE
        SYNTAX  INTEGER
        ACCESS  read-only
        STATUS 	mandatory
        DESCRIPTION
        "This value indicates an index of a specific PM Interval"
        ::= { genEquipPmRadioMRMCEntry 3 }

genEquipPmRadioMRMCIfIndex OBJECT-TYPE
		SYNTAX  INTEGER
		ACCESS  read-only
		STATUS 	mandatory
		DESCRIPTION
		"This value indicates the interface index of a specific RFU interface (as appears in the ifTable)"
		::= { genEquipPmRadioMRMCEntry 4 }

genEquipPmRadioMRMCMinProfile	OBJECT-TYPE
        SYNTAX		INTEGER
        ACCESS  	read-only
        STATUS 		mandatory
        DESCRIPTION
		"Minimum MRMC profile."
		::= { genEquipPmRadioMRMCEntry 5 }

genEquipPmRadioMRMCMaxProfile	OBJECT-TYPE
        SYNTAX		INTEGER
        ACCESS  	read-only
        STATUS 		mandatory
        DESCRIPTION
		"Maximum MRMC profile"
		::= { genEquipPmRadioMRMCEntry 6 }

genEquipPmRadioMRMCMinBitrate	OBJECT-TYPE
        SYNTAX		INTEGER
        ACCESS  	read-only
        STATUS 		mandatory
        DESCRIPTION
		"Minimum MRMC nominal bitrate (Units are Kbps)"
		::= { genEquipPmRadioMRMCEntry 7 }

genEquipPmRadioMRMCMaxBitrate	OBJECT-TYPE
        SYNTAX		INTEGER
        ACCESS  	read-only
        STATUS 		mandatory
        DESCRIPTION
		"Maximum MRMC nominal bitrate (Units are Kbps)"
		::= { genEquipPmRadioMRMCEntry 8 }

genEquipPmRadioMRMCMinTDMIf	OBJECT-TYPE
        SYNTAX		INTEGER
        ACCESS  	read-only
        STATUS 		mandatory
        DESCRIPTION
		"Minimum number of allocated TDM channels"
		::= { genEquipPmRadioMRMCEntry 9 }

genEquipPmRadioMRMCMaxTDMIf	OBJECT-TYPE
        SYNTAX		INTEGER
        ACCESS  	read-only
        STATUS 		mandatory
        DESCRIPTION
		"Maximum number of allocated TDM channels"
		::= { genEquipPmRadioMRMCEntry 10 }

genEquipPmRadioMRMCIDF  OBJECT-TYPE
		SYNTAX  Integrity
        ACCESS  read-only
        STATUS mandatory
        DESCRIPTION
		"This value indicates if the IDF (Invalid Data Flag), was set."
        ::= { genEquipPmRadioMRMCEntry 11 }



-- 	Radio E1/T1 PM Group	
genEquipPmRadioTDM	OBJECT IDENTIFIER ::= {genEquipPmRadio 2}

-- Radio E1/T1 TDM PM Table
genEquipPmRadioTDMTable  OBJECT-TYPE
        SYNTAX  SEQUENCE OF GenEquipPmRadioTDMEntry
        ACCESS  not-accessible
        STATUS mandatory
       DESCRIPTION
        "The PM table of logical TDM channels within the Radio link"
        ::= { genEquipPmRadioTDM 1 }

genEquipPmRadioTDMEntry OBJECT-TYPE
        SYNTAX GenEquipPmRadioTDMEntry
        ACCESS  not-accessible
        STATUS mandatory
        DESCRIPTION
        "The PM table of logical TDM channels within the Radio link"
        INDEX { genEquipPmRadioTDMPmType, ifIndex, genEquipPmRadioTDMInterval }
        ::= { genEquipPmRadioTDMTable 1 }

GenEquipPmRadioTDMEntry ::=
            SEQUENCE {
		genEquipPmRadioTDMPmType				PmTableType,
		genEquipPmRadioTDMInterval				INTEGER,
        genEquipPmRadioTDMRadioUAS				INTEGER,
        genEquipPmRadioTDMIDF					Integrity
	}

genEquipPmRadioTDMPmType OBJECT-TYPE
        SYNTAX  PmTableType
        ACCESS  read-only
        STATUS 	mandatory
        DESCRIPTION
        "This value indicates the PM Type table to access, 15 min, current 15 min, 24 hours or current 24 hours"
        ::= { genEquipPmRadioTDMEntry 1 }

genEquipPmRadioTDMInterval OBJECT-TYPE
        SYNTAX  INTEGER
        ACCESS  read-only
        STATUS 	mandatory
        DESCRIPTION
        "The interval of the PM"
        ::= { genEquipPmRadioTDMEntry 2 }
		
genEquipPmRadioTDMRadioUAS	OBJECT-TYPE
        SYNTAX		INTEGER
        ACCESS  	read-only
        STATUS 		mandatory
        DESCRIPTION
		"TDM channel UAS (unavailable seconds)"
		::= { genEquipPmRadioTDMEntry 3 }

genEquipPmRadioTDMIDF  OBJECT-TYPE
		SYNTAX  Integrity
        ACCESS  read-only
        STATUS mandatory
        DESCRIPTION
		"This value indicates if the IDF (Invalid Data Flag), was set."
        ::= { genEquipPmRadioTDMEntry 4 }
 
 
-- 	Radio Ethernet PM Group	
genEquipPmRadioEthernet	OBJECT IDENTIFIER ::= {genEquipPmRadio 3}

-- Radio E1/T1 TDM PM Table
genEquipPmRadioEthernetTable  OBJECT-TYPE
        SYNTAX  SEQUENCE OF GenEquipPmRadioEthernetEntry
        ACCESS  not-accessible
        STATUS mandatory
       DESCRIPTION
        "The Ethernet PMs on the radio link"
        ::= { genEquipPmRadioEthernet 1 }

genEquipPmRadioEthernetEntry OBJECT-TYPE
        SYNTAX GenEquipPmRadioEthernetEntry
        ACCESS  not-accessible
        STATUS mandatory
        DESCRIPTION
        "The Ethernet PMs on the radio link"
        INDEX { genEquipPmRadioEthernetPmType, ifIndex, genEquipPmRadioEthernetInterval }
        ::= { genEquipPmRadioEthernetTable 1 }

GenEquipPmRadioEthernetEntry ::=
            SEQUENCE {
		genEquipPmRadioEthernetPmType				PmTableType,
		genEquipPmRadioEthernetInterval				INTEGER,
		genEquipPmRadioEthernetFrameErrorRate		INTEGER,
		genEquipPmRadioEthernetPeakThroughput		INTEGER,
		genEquipPmRadioEthernetAverageThroughput	INTEGER,
		genEquipPmRadioEthernetExceedThroughput		INTEGER,
		genEquipPmRadioEthernetPeakCapacity			INTEGER,
		genEquipPmRadioEthernetAverageCapacity		INTEGER,
		genEquipPmRadioEthernetExceedCapacity		INTEGER,
		genEquipPmRadioEthernetPeakUtilization		INTEGER,
		genEquipPmRadioEthernetAverageUtilization	INTEGER,
		genEquipPmRadioEthernetExceedUtilization	INTEGER,
        genEquipPmRadioEthernetIDF					Integrity
	}

genEquipPmRadioEthernetPmType OBJECT-TYPE
        SYNTAX  PmTableType
        ACCESS  read-only
        STATUS 	mandatory
        DESCRIPTION
        "This value indicates the PM Type table to access, 15 min, current 15 min, 24 hours or current 24 hours"
        ::= { genEquipPmRadioEthernetEntry 1 }
		

genEquipPmRadioEthernetInterval OBJECT-TYPE
        SYNTAX  INTEGER
        ACCESS  read-only
        STATUS 	mandatory
        DESCRIPTION
        "The interval of the PM"
        ::= { genEquipPmRadioEthernetEntry 2 }

genEquipPmRadioEthernetFrameErrorRate	OBJECT-TYPE
        SYNTAX		INTEGER
        ACCESS  	read-only
        STATUS 		mandatory
        DESCRIPTION
		"Ethernet Frame Error Rate PM"
		::= { genEquipPmRadioEthernetEntry 3 }

genEquipPmRadioEthernetPeakThroughput	OBJECT-TYPE
        SYNTAX		INTEGER
        ACCESS  	read-only
        STATUS 		mandatory
        DESCRIPTION
		"Ethernet Peak throughput PM (Units are bits per second)"
		::= { genEquipPmRadioEthernetEntry 4 }

genEquipPmRadioEthernetAverageThroughput	OBJECT-TYPE
        SYNTAX		INTEGER
        ACCESS  	read-only
        STATUS 		mandatory
        DESCRIPTION
		"Ethernet Average throughput PM (Units are bits per second)"
		::= { genEquipPmRadioEthernetEntry 5 }

genEquipPmRadioEthernetExceedThroughput	OBJECT-TYPE
        SYNTAX		INTEGER
        ACCESS  	read-only
        STATUS 		mandatory
        DESCRIPTION
		"Ethernet Exceed throughput PM"
		::= { genEquipPmRadioEthernetEntry 6 }

genEquipPmRadioEthernetPeakCapacity	OBJECT-TYPE
        SYNTAX		INTEGER
        ACCESS  	read-only
        STATUS 		mandatory
        DESCRIPTION
		"Ethernet Peak capacity PM (in bps)"
		::= { genEquipPmRadioEthernetEntry 7 }

genEquipPmRadioEthernetAverageCapacity	OBJECT-TYPE
        SYNTAX		INTEGER
        ACCESS  	read-only
        STATUS 		mandatory
        DESCRIPTION
		"Ethernet Average capacity PM (in bps)"
		::= { genEquipPmRadioEthernetEntry 8 }

genEquipPmRadioEthernetExceedCapacity	OBJECT-TYPE
        SYNTAX		INTEGER
        ACCESS  	read-only
        STATUS 		mandatory
        DESCRIPTION
		"Ethernet Exceed capacity PM"
		::= { genEquipPmRadioEthernetEntry 9 }

genEquipPmRadioEthernetPeakUtilization	OBJECT-TYPE
        SYNTAX		INTEGER
        ACCESS  	read-only
        STATUS 		mandatory
        DESCRIPTION
		"Ethernet Peak utilization PM (%)"
		::= { genEquipPmRadioEthernetEntry 10 }

genEquipPmRadioEthernetAverageUtilization	OBJECT-TYPE
        SYNTAX		INTEGER
        ACCESS  	read-only
        STATUS 		mandatory
        DESCRIPTION
		"Ethernet Average utilization PM (%)"
		::= { genEquipPmRadioEthernetEntry 11 }

genEquipPmRadioEthernetExceedUtilization	OBJECT-TYPE
        SYNTAX		INTEGER
        ACCESS  	read-only
        STATUS 		mandatory
        DESCRIPTION
		"Ethernet Exceed utilization PM"
		::= { genEquipPmRadioEthernetEntry 12 }

genEquipPmRadioEthernetIDF  OBJECT-TYPE
		SYNTAX  Integrity
		ACCESS  read-only
		STATUS mandatory
		DESCRIPTION
		"This value indicates if the IDF (Invalid Data Flag), was set."
		::= { genEquipPmRadioEthernetEntry 13 }

-- 	Radio Thresholds

genEquipPmRadioEthernetThresholdTable  OBJECT-TYPE
        SYNTAX  SEQUENCE OF GenEquipPmRadioEthernetThresholdEntry
        ACCESS  not-accessible
        STATUS mandatory
       DESCRIPTION
        "The Ethernet PMs on the radio link"
        ::= { genEquipPmRadioEthernet 2 }

genEquipPmRadioEthernetThresholdEntry OBJECT-TYPE
        SYNTAX GenEquipPmRadioEthernetThresholdEntry
        ACCESS  not-accessible
        STATUS mandatory
        DESCRIPTION
        "The Ethernet PMs on the radio link"
        INDEX { genEquipRadioCfgRadioId }
        ::= { genEquipPmRadioEthernetThresholdTable 1 }

GenEquipPmRadioEthernetThresholdEntry ::=
	SEQUENCE {
		genEquipPmRadioEthernetThresholdThroughput		INTEGER,
		genEquipPmRadioEthernetThresholdCapacity		INTEGER,
		genEquipPmRadioEthernetThresholdUtilization		INTEGER
	}

genEquipPmRadioEthernetThresholdThroughput  OBJECT-TYPE
		SYNTAX  INTEGER (0..1000)
        ACCESS  read-write
        STATUS mandatory
        DESCRIPTION
		"Ethernet Throughput threshold (in Mbps)"
        ::= { genEquipPmRadioEthernetThresholdEntry 1 }
		
genEquipPmRadioEthernetThresholdCapacity  OBJECT-TYPE
		SYNTAX  INTEGER (0..1000)
        ACCESS  read-write
        STATUS mandatory
        DESCRIPTION
		"Ethernet capacity threshold (in Mbps)"
        ::= { genEquipPmRadioEthernetThresholdEntry 2 }
		
genEquipPmRadioEthernetThresholdUtilization  OBJECT-TYPE
		SYNTAX  INTEGER {
			 above-0(0),
			 above-20(1),
			 above-40(2),
			 above-60(3),
			 above-80(4),
			 no-threshold(5)}
        ACCESS  read-write
        STATUS mandatory
        DESCRIPTION
		"Ethernet utilization threshold (in percentage)."
        ::= { genEquipPmRadioEthernetThresholdEntry 3 }

-- 	The Ethernet ETM PMs on the radio link
genEquipPmRadioEthernetEtmTable  OBJECT-TYPE
        SYNTAX  SEQUENCE OF GenEquipPmRadioEthernetEtmEntry
        ACCESS  not-accessible
        STATUS mandatory
       DESCRIPTION
        "The Ethernet PMs on the radio link"
        ::= { genEquipPmRadioEthernet 3 }

genEquipPmRadioEthernetEtmEntry OBJECT-TYPE
        SYNTAX GenEquipPmRadioEthernetEtmEntry
        ACCESS  not-accessible
        STATUS mandatory
        DESCRIPTION
        "The entry of Ethernet ETM PMs on the radio link"
        INDEX { genEquipPmRadioEthernetEtmPmType, genEquipPmRadioEthernetEtmPmQueueIndex, genEquipPmRadioEthernetEtmInterval }
        ::= { genEquipPmRadioEthernetEtmTable 1 }

GenEquipPmRadioEthernetEtmEntry ::=
	SEQUENCE {
		genEquipPmRadioEthernetEtmPmType		
			PmTableType,
		genEquipPmRadioEthernetEtmPmQueueIndex
			INTEGER,
		genEquipPmRadioEthernetEtmInterval		
			INTEGER,
		genEquipPmRadioEthernetEtmPmMaxGreenBytesPassed
			INTEGER,
		genEquipPmRadioEthernetEtmPmAvgGreenBytesPassed
			INTEGER,
		genEquipPmRadioEthernetEtmPmMaxGreenFramesDropped
			INTEGER,
		genEquipPmRadioEthernetEtmPmAvgGreenFramesDropped
			INTEGER,
		genEquipPmRadioEthernetEtmPmMaxYellowBytesPassed
			INTEGER,
		genEquipPmRadioEthernetEtmPmAvgYellowBytesPassed
			INTEGER,
		genEquipPmRadioEthernetEtmPmMaxYellowFramesDropped
			INTEGER,
		genEquipPmRadioEthernetEtmPmAvgYellowFramesDropped
			INTEGER,
		genEquipPmRadioEthernetEtmPmMaxRedFramesDropped
			INTEGER,
		genEquipPmRadioEthernetEtmPmAvgRedFramesDropped
			INTEGER,
		genEquipPmRadioEthernetEtmPmIDF
			Integrity

	}

genEquipPmRadioEthernetEtmPmType  OBJECT-TYPE
		SYNTAX  PmTableType
        ACCESS  read-only
        STATUS mandatory
        DESCRIPTION
		"This value indicates the PM Type table to access, 15 min, current 15 min, 24 hours or current 24 hours"
        ::= { genEquipPmRadioEthernetEtmEntry 1 }
		
genEquipPmRadioEthernetEtmPmQueueIndex  OBJECT-TYPE
		SYNTAX  INTEGER (1..8)
        ACCESS  read-only
        STATUS mandatory
        DESCRIPTION
		"Queue index"
        ::= { genEquipPmRadioEthernetEtmEntry 2 }
		
genEquipPmRadioEthernetEtmInterval  OBJECT-TYPE
		SYNTAX  INTEGER (0..96)
        ACCESS  read-only
        STATUS mandatory
        DESCRIPTION
		"The interval of the PM."
        ::= { genEquipPmRadioEthernetEtmEntry 3 }

genEquipPmRadioEthernetEtmPmMaxGreenBytesPassed  OBJECT-TYPE
		SYNTAX  INTEGER 
        ACCESS  read-only
        STATUS mandatory
        DESCRIPTION
		"Maximum Green Traffic Passed Bytes."
        ::= { genEquipPmRadioEthernetEtmEntry 4 }

genEquipPmRadioEthernetEtmPmAvgGreenBytesPassed  OBJECT-TYPE
		SYNTAX  INTEGER 
        ACCESS  read-only
        STATUS mandatory
        DESCRIPTION
		"Average Green Traffic Passed Bytes."
        ::= { genEquipPmRadioEthernetEtmEntry 5 }

genEquipPmRadioEthernetEtmPmMaxGreenFramesDropped  OBJECT-TYPE
		SYNTAX  INTEGER 
        ACCESS  read-only
        STATUS mandatory
        DESCRIPTION
		"Maximum Green Traffic Frames Droped by WRED."
        ::= { genEquipPmRadioEthernetEtmEntry 6 }

genEquipPmRadioEthernetEtmPmAvgGreenFramesDropped  OBJECT-TYPE
		SYNTAX  INTEGER 
        ACCESS  read-only
        STATUS mandatory
        DESCRIPTION
		"Average Green Traffic Frames Droped by WRED."
        ::= { genEquipPmRadioEthernetEtmEntry 7 }

genEquipPmRadioEthernetEtmPmMaxYellowBytesPassed  OBJECT-TYPE
		SYNTAX  INTEGER 
        ACCESS  read-only
        STATUS mandatory
        DESCRIPTION
		"Maximum Yellow Traffic Passed Bytes."
        ::= { genEquipPmRadioEthernetEtmEntry 8 }

genEquipPmRadioEthernetEtmPmAvgYellowBytesPassed  OBJECT-TYPE
		SYNTAX  INTEGER 
        ACCESS  read-only
        STATUS mandatory
        DESCRIPTION
		"Average Yellow Traffic Passed Bytes."
        ::= { genEquipPmRadioEthernetEtmEntry 9 }

genEquipPmRadioEthernetEtmPmMaxYellowFramesDropped  OBJECT-TYPE
		SYNTAX  INTEGER 
        ACCESS  read-only
        STATUS mandatory
        DESCRIPTION
		"Maximum Yellow Traffic Frames Droped by WRED."
        ::= { genEquipPmRadioEthernetEtmEntry 10 }

genEquipPmRadioEthernetEtmPmAvgYellowFramesDropped  OBJECT-TYPE
		SYNTAX  INTEGER 
        ACCESS  read-only
        STATUS mandatory
        DESCRIPTION
		"Average Yellow Traffic Frames Droped by WRED."
        ::= { genEquipPmRadioEthernetEtmEntry 11 }

genEquipPmRadioEthernetEtmPmMaxRedFramesDropped  OBJECT-TYPE
		SYNTAX  INTEGER 
        ACCESS  read-only
        STATUS mandatory
        DESCRIPTION
		"Maximum Red Traffic Frames Dropped."
        ::= { genEquipPmRadioEthernetEtmEntry 12 }

genEquipPmRadioEthernetEtmPmAvgRedFramesDropped  OBJECT-TYPE
		SYNTAX  INTEGER 
        ACCESS  read-only
        STATUS mandatory
        DESCRIPTION
		"Average Red Traffic Frames Dropped."
        ::= { genEquipPmRadioEthernetEtmEntry 13 }

genEquipPmRadioEthernetEtmPmIDF  OBJECT-TYPE
		SYNTAX  Integrity
        ACCESS  read-only
        STATUS mandatory
        DESCRIPTION
		"This value indicates if the IDF (Invalid Data Flag), was set."
        ::= { genEquipPmRadioEthernetEtmEntry 14 }

		
--        
genEquipPmRadioMSETable  OBJECT-TYPE
        SYNTAX  SEQUENCE OF GenEquipPmRadioMSEEntry
        ACCESS  not-accessible
        STATUS mandatory
       DESCRIPTION
        "Radio MSE PM"
        ::= { genEquipPmRadio 4 }

genEquipPmRadioMSEEntry OBJECT-TYPE
        SYNTAX GenEquipPmRadioMSEEntry
        ACCESS  not-accessible
        STATUS mandatory
        DESCRIPTION
        "Radio MSE PM"
        INDEX { genEquipPmRadioMSEPmType, ifIndex, genEquipPmRadioMSEInterval }
        ::= { genEquipPmRadioMSETable 1 }

GenEquipPmRadioMSEEntry ::=
            SEQUENCE {
		genEquipPmRadioMSEPmType		PmTableType,
		genEquipPmRadioMSEInterval		INTEGER,
        genEquipPmRadioMSEMinMse		INTEGER,
        genEquipPmRadioMSEMaxMse		INTEGER,
        genEquipPmRadioMSEexceeded		INTEGER,
        genEquipPmRadioMSEIDF		Integrity
	}       
	
genEquipPmRadioMSEPmType OBJECT-TYPE
        SYNTAX  PmTableType
        ACCESS  read-only
        STATUS 	mandatory
        DESCRIPTION
        "This value indicates the PM Type table to access, 15 min, current 15 min, 24 hours or current 24 hours"
        ::= { genEquipPmRadioMSEEntry 1 }

genEquipPmRadioMSEInterval OBJECT-TYPE
        SYNTAX  INTEGER
        ACCESS  read-only
        STATUS 	mandatory
        DESCRIPTION
        "The interval of the PM"
        ::= { genEquipPmRadioMSEEntry 2 }      
        
genEquipPmRadioMSEMinMse OBJECT-TYPE
        SYNTAX  INTEGER
        ACCESS  read-only
        STATUS 	mandatory
        DESCRIPTION
        "This parameter holds the minimum MSE value detected in  the interval."
        ::= { genEquipPmRadioMSEEntry 3 }
        
genEquipPmRadioMSEMaxMse OBJECT-TYPE
        SYNTAX  INTEGER
        ACCESS  read-only
        STATUS 	mandatory
        DESCRIPTION
        "This parameter holds the maximum MSE value detected in  the interval."
        ::= { genEquipPmRadioMSEEntry 4 }
        
genEquipPmRadioMSEexceeded OBJECT-TYPE
        SYNTAX  INTEGER
        ACCESS  read-only
        STATUS 	mandatory
        DESCRIPTION
        "This parameter holds the number of seconds that the MSE exceeded the configured threshold."
        ::= { genEquipPmRadioMSEEntry 5 }      
        
genEquipPmRadioMSEIDF  OBJECT-TYPE
		SYNTAX  Integrity
        ACCESS  read-only
        STATUS mandatory
        DESCRIPTION
		"This value indicates if the IDF (Invalid Data Flag), was set."
        ::= { genEquipPmRadioMSEEntry 6 }


--  Radio Thresold

genEquipPmRadioThresholdTable  OBJECT-TYPE
        SYNTAX  SEQUENCE OF GenEquipPmRadioThresholdEntry
        ACCESS  not-accessible
        STATUS mandatory
       DESCRIPTION
        "Radio MSE PM"
        ::= { genEquipPmRadio 5 }

genEquipPmRadioThresholdEntry OBJECT-TYPE
        SYNTAX GenEquipPmRadioThresholdEntry
        ACCESS  not-accessible
        STATUS mandatory
        DESCRIPTION
        "Radio MSE PM"
        INDEX { genEquipRadioCfgRadioId }
        ::= { genEquipPmRadioThresholdTable 1 }

GenEquipPmRadioThresholdEntry ::=
            SEQUENCE {
		genEquipPmRadioThresholdMSE		INTEGER,
		genEquipPmRadioThresholdRSL1	INTEGER,
        genEquipPmRadioThresholdRSL2 	INTEGER,
        genEquipPmRadioThresholdTSL		INTEGER,
        genEquipPmRadioThresholdXPI		INTEGER
	}       
	
genEquipPmRadioThresholdMSE OBJECT-TYPE
        SYNTAX  INTEGER
        ACCESS  read-write
        STATUS 	mandatory
        DESCRIPTION
        "The threshold above which MSE exceeded seconds will be counted"
        ::= { genEquipPmRadioThresholdEntry 1 }

genEquipPmRadioThresholdRSL1 OBJECT-TYPE
        SYNTAX  INTEGER
        ACCESS  read-write
        STATUS 	mandatory
        DESCRIPTION
        "The threshold below which RSL 1 exceeded seconds will be counted"
        ::= { genEquipPmRadioThresholdEntry 2 }      
        
genEquipPmRadioThresholdRSL2 OBJECT-TYPE
        SYNTAX  INTEGER
        ACCESS  read-write
        STATUS 	mandatory
        DESCRIPTION
        "The threshold below which RSL 2 exceeded seconds will be counted"
        ::= { genEquipPmRadioThresholdEntry 3 }
        
genEquipPmRadioThresholdTSL OBJECT-TYPE
        SYNTAX  INTEGER
        ACCESS  read-write
        STATUS 	mandatory
        DESCRIPTION
        "The threshold above which TSL exceeded seconds will be counted"
        ::= { genEquipPmRadioThresholdEntry 4 }
        
genEquipPmRadioThresholdXPI OBJECT-TYPE
        SYNTAX  INTEGER
        ACCESS  read-write
        STATUS 	mandatory
        DESCRIPTION
        "The threshold above which XPI exceeded seconds will be counted"
        ::= { genEquipPmRadioThresholdEntry 5 }
        

--  Radio XPIC

genEquipPmRadioXPITable  OBJECT-TYPE
        SYNTAX  SEQUENCE OF GenEquipPmRadioXPIEntry
        ACCESS  not-accessible
        STATUS mandatory
       DESCRIPTION
        "Radio XPIC PM"
        ::= { genEquipPmRadio 6 }

genEquipPmRadioXPIEntry OBJECT-TYPE
        SYNTAX GenEquipPmRadioXPIEntry
        ACCESS  not-accessible
        STATUS mandatory
        DESCRIPTION
        "Radio XPIC PM"
        INDEX { genEquipPmRadioXPIPmType, ifIndex, genEquipPmRadioXPIPmInterval }
        ::= { genEquipPmRadioXPITable 1 }

GenEquipPmRadioXPIEntry ::=
            SEQUENCE {
		genEquipPmRadioXPIPmType			PmTableType,
		genEquipPmRadioXPIPmInterval		INTEGER,
        genEquipPmRadioXPIPmMinXPI 			INTEGER,
        genEquipPmRadioXPIPmMaxXPI			INTEGER,
		genEquipPmRadioXPIBelowThreshold	INTEGER,
        genEquipPmRadioXPIIDF		Integrity
	}       
	
genEquipPmRadioXPIPmType OBJECT-TYPE
        SYNTAX  PmTableType
        ACCESS  read-write
        STATUS 	mandatory
        DESCRIPTION
        "The interval of the PM"
        ::= { genEquipPmRadioXPIEntry 1 }

genEquipPmRadioXPIPmInterval OBJECT-TYPE
        SYNTAX  INTEGER
        ACCESS  read-write
        STATUS 	mandatory
        DESCRIPTION
        "The threshold below which RSL 1 exceeded seconds will be counted"
        ::= { genEquipPmRadioXPIEntry 2 }      
        
genEquipPmRadioXPIPmMinXPI OBJECT-TYPE
        SYNTAX  INTEGER
        ACCESS  read-write
        STATUS 	mandatory
        DESCRIPTION
        "This parameter holds the minimum XPI value detected in the interval"
        ::= { genEquipPmRadioXPIEntry 3 }
        
genEquipPmRadioXPIPmMaxXPI OBJECT-TYPE
        SYNTAX  INTEGER
        ACCESS  read-write
        STATUS 	mandatory
        DESCRIPTION
        "This parameter holds the maximum XPI value detected in the interval"
        ::= { genEquipPmRadioXPIEntry 4 }
        
genEquipPmRadioXPIBelowThreshold OBJECT-TYPE
        SYNTAX  INTEGER
        ACCESS  read-write
        STATUS 	mandatory
        DESCRIPTION
        "This parameter holds the number of seconds in the interval that the XPI value was below the configured threshold."
        ::= { genEquipPmRadioXPIEntry 5 }

genEquipPmRadioXPIIDF  OBJECT-TYPE
		SYNTAX  Integrity
        ACCESS  read-only
        STATUS mandatory
        DESCRIPTION
		"This value indicates if the IDF (Invalid Data Flag), was set."
        ::= { genEquipPmRadioXPIEntry 6 }
        
		
-- 	TDM (E1/T1) PM Group	
genEquipPmTDM	OBJECT IDENTIFIER ::= {genEquipPmAll 5}

-- 	TDM (E1/T1) PM Table
genEquipPmTdmTable  OBJECT-TYPE
        SYNTAX  SEQUENCE OF GenEquipPmTdmEntry
        ACCESS  not-accessible
        STATUS mandatory
       DESCRIPTION
        "The line TDM PM table"
        ::= { genEquipPmTDM 1 }

genEquipPmTdmEntry OBJECT-TYPE
        SYNTAX GenEquipPmTdmEntry
        ACCESS  not-accessible
        STATUS mandatory
        DESCRIPTION
        "The line TDM PM table"
        INDEX { genEquipPmTdmPmType, ifIndex, genEquipPmTdmInterval }
        ::= { genEquipPmTdmTable 1 }

GenEquipPmTdmEntry ::=
            SEQUENCE {
		genEquipPmTdmPmType				PmTableType,
		genEquipPmTdmInterval			INTEGER,
        genEquipPmTdmES					INTEGER,
        genEquipPmTdmSES				INTEGER,
        genEquipPmTdmUAS				INTEGER,
        genEquipPmTdmBBE				INTEGER,
        genEquipPmTdmIDF				Integrity
	}

genEquipPmTdmPmType OBJECT-TYPE
        SYNTAX  PmTableType
        ACCESS  read-only
        STATUS 	mandatory
        DESCRIPTION
        "This value indicates the PM Type table to access, 15 min, current 15 min, 24 hours or current 24 hours"
        ::= { genEquipPmTdmEntry 1 }

genEquipPmTdmInterval OBJECT-TYPE
        SYNTAX  INTEGER
        ACCESS  read-only
        STATUS 	mandatory
        DESCRIPTION
        "The interval of the PM"
        ::= { genEquipPmTdmEntry 2 }
		
genEquipPmTdmES	OBJECT-TYPE
        SYNTAX		INTEGER
        ACCESS  	read-only
        STATUS 		mandatory
        DESCRIPTION
		"ES PM (Errored second)"
		::= { genEquipPmTdmEntry 3 }

genEquipPmTdmSES	OBJECT-TYPE
        SYNTAX		INTEGER
        ACCESS  	read-only
        STATUS 		mandatory
        DESCRIPTION
		"SES PM (Severe Errored Seconds)"
		::= { genEquipPmTdmEntry 4 }

genEquipPmTdmUAS	OBJECT-TYPE
        SYNTAX		INTEGER
        ACCESS  	read-only
        STATUS 		mandatory
        DESCRIPTION
		"UAS PM (Unavailable Seconds)."
		::= { genEquipPmTdmEntry 5 }

genEquipPmTdmBBE	OBJECT-TYPE
        SYNTAX		INTEGER
        ACCESS  	read-only
        STATUS 		mandatory
        DESCRIPTION
		"BBE PM (Background Block Errors)"
		::= { genEquipPmTdmEntry 6 }

genEquipPmTdmIDF  OBJECT-TYPE
		SYNTAX  Integrity
        ACCESS  read-only
        STATUS mandatory
        DESCRIPTION
		"This value indicates if the IDF (Invalid Data Flag), was set."
        ::= { genEquipPmTdmEntry 7 }

-- 	SDH/Sonet PM Group	
genEquipPmSDH	OBJECT IDENTIFIER ::= {genEquipPmAll 6}

genEquipPmSdhTable  OBJECT-TYPE
        SYNTAX  SEQUENCE OF GenEquipPmSdhEntry
        ACCESS  not-accessible
        STATUS mandatory
       DESCRIPTION
        "The line SDH PM table."
        ::= { genEquipPmSDH 1 }

genEquipPmSdhEntry OBJECT-TYPE
        SYNTAX GenEquipPmSdhEntry
        ACCESS  not-accessible
        STATUS mandatory
        DESCRIPTION
        "The line SDH PM table."
        INDEX { genEquipPmSdhPmType, ifIndex, genEquipPmSdhInterval }
        ::= { genEquipPmSdhTable 1 }

GenEquipPmSdhEntry ::=
            SEQUENCE {
		genEquipPmSdhPmType				PmTableType,
		genEquipPmSdhInterval			INTEGER,
        genEquipPmSdhES					INTEGER,
        genEquipPmSdhSES				INTEGER,
        genEquipPmSdhEB					INTEGER,
        genEquipPmSdhBBE				INTEGER,
        genEquipPmSdhIDF				Integrity
	}

genEquipPmSdhPmType OBJECT-TYPE
        SYNTAX  PmTableType
        ACCESS  read-only
        STATUS 	mandatory
        DESCRIPTION
        "This value indicates the PM Type table to access, 15 min, current 15 min, 24 hours or current 24 hours."
        ::= { genEquipPmSdhEntry 1 }

genEquipPmSdhInterval OBJECT-TYPE
        SYNTAX  INTEGER
        ACCESS  read-only
        STATUS 	mandatory
        DESCRIPTION
        "The interval of the PM."
        ::= { genEquipPmSdhEntry 2 }
		
genEquipPmSdhES	OBJECT-TYPE
        SYNTAX		INTEGER
        ACCESS  	read-only
        STATUS 		mandatory
        DESCRIPTION
		"ES STM-1/OC-3 PM."
		::= { genEquipPmSdhEntry 3 }

genEquipPmSdhSES	OBJECT-TYPE
        SYNTAX		INTEGER
        ACCESS  	read-only
        STATUS 		mandatory
        DESCRIPTION
		"SES STM-1/OC-3 PM."
		::= { genEquipPmSdhEntry 4 }

genEquipPmSdhEB	OBJECT-TYPE
        SYNTAX		INTEGER
        ACCESS  	read-only
        STATUS 		mandatory
        DESCRIPTION
		"EB STM-1/OC-3 PM (Errored block)."
		::= { genEquipPmSdhEntry 5 }

genEquipPmSdhBBE	OBJECT-TYPE
        SYNTAX		INTEGER
        ACCESS  	read-only
        STATUS 		mandatory
        DESCRIPTION
		"BBE PM (background errored block STM-1/OC-3 PM or CVL PM (code violation line) when using OC-3."
		::= { genEquipPmSdhEntry 6 }

genEquipPmSdhIDF  OBJECT-TYPE
		SYNTAX  Integrity
        ACCESS  read-only
        STATUS mandatory
        DESCRIPTION
		"This value indicates if the IDF (Invalid Data Flag), was set."
        ::= { genEquipPmSdhEntry 7 }


-- 	Trails PM Group	
genEquipPmTrails	OBJECT IDENTIFIER ::= {genEquipPmAll 7}

-- 	TDM (E1/T1) PM Table
genEquipPmTrailsEndPointTable  OBJECT-TYPE
        SYNTAX  SEQUENCE OF GenEquipPmTrailsEndPointEntry
        ACCESS  not-accessible
        STATUS mandatory
       DESCRIPTION
        "PM table of the E1/T1 trails."
        ::= { genEquipPmTrails 1 }

genEquipPmTrailsEndPointEntry OBJECT-TYPE
        SYNTAX GenEquipPmTrailsEndPointEntry
        ACCESS  not-accessible
        STATUS mandatory
        DESCRIPTION
        "PM table of the E1/T1 trails."
        INDEX { genEquipPmTrailsEndPointPmType, genEquipPmTrailsEndPointId, genEquipPmTrailsEndPointEPId, genEquipPmTrailsEndPointInterval }
        ::= { genEquipPmTrailsEndPointTable 1 }

GenEquipPmTrailsEndPointEntry ::=
            SEQUENCE {
		genEquipPmTrailsEndPointPmType					PmTableType,
		genEquipPmTrailsEndPointId						DisplayString,
		genEquipPmTrailsEndPointEPId					INTEGER,
		genEquipPmTrailsEndPointInterval				INTEGER,
        genEquipPmTrailsEndPointES						INTEGER,
        genEquipPmTrailsEndPointSES						INTEGER,
        genEquipPmTrailsEndPointUAS						INTEGER,
        genEquipPmTrailsEndPointBBE						INTEGER,
        genEquipPmTrailsEndPointNoOfSwitches			INTEGER,
        genEquipPmTrailsEndPointActivePathCounts		INTEGER,
        genEquipPmTrailsEndPointIDF						Integrity
	}

genEquipPmTrailsEndPointPmType OBJECT-TYPE
        SYNTAX  PmTableType
        ACCESS  read-only
        STATUS 	mandatory
        DESCRIPTION
        "This value indicates the PM Type table to access, 15 min, current 15 min, 24 hours or current 24 hours."
        ::= { genEquipPmTrailsEndPointEntry 1 }

genEquipPmTrailsEndPointId OBJECT-TYPE
        SYNTAX  DisplayString
        ACCESS  read-only
        STATUS 	mandatory
        DESCRIPTION
        "This value indicates the trail id."
        ::= { genEquipPmTrailsEndPointEntry 2 }
		
genEquipPmTrailsEndPointEPId OBJECT-TYPE
        SYNTAX  INTEGER
        ACCESS  read-only
        STATUS 	mandatory
        DESCRIPTION
        "This value indicates the end point number for this trail.
        If the trail is protected, there will be two end points for the trail (primary path and the secondary path)."
        ::= { genEquipPmTrailsEndPointEntry 3 }
		
genEquipPmTrailsEndPointInterval OBJECT-TYPE
        SYNTAX  INTEGER
        ACCESS  read-only
        STATUS 	mandatory
        DESCRIPTION
        "The interval of the PM."
        ::= { genEquipPmTrailsEndPointEntry 4 }
		
genEquipPmTrailsEndPointES	OBJECT-TYPE
        SYNTAX		INTEGER
        ACCESS  	read-only
        STATUS 		mandatory
        DESCRIPTION
		"ES PM (Errored Seconds)."
		::= { genEquipPmTrailsEndPointEntry 5 }

genEquipPmTrailsEndPointSES	OBJECT-TYPE
        SYNTAX		INTEGER
        ACCESS  	read-only
        STATUS 		mandatory
        DESCRIPTION
		"SES PM (Severe Errored Seconds)."
		::= { genEquipPmTrailsEndPointEntry 6 }

genEquipPmTrailsEndPointUAS	OBJECT-TYPE
        SYNTAX		INTEGER
        ACCESS  	read-only
        STATUS 		mandatory
        DESCRIPTION
		"UAS PM (Unavailable Seconds)."
		::= { genEquipPmTrailsEndPointEntry 7 }

genEquipPmTrailsEndPointBBE	OBJECT-TYPE
        SYNTAX		INTEGER
        ACCESS  	read-only
        STATUS 		mandatory
        DESCRIPTION
		"BBE PM (Background Block Errors)."
		::= { genEquipPmTrailsEndPointEntry 8 }

genEquipPmTrailsEndPointNoOfSwitches	OBJECT-TYPE
        SYNTAX		INTEGER
        ACCESS  	read-only
        STATUS 		mandatory
        DESCRIPTION
		"A counter of the number of SNCP switches (between primary and secondary paths) that trail had in the relevant interval."
		::= { genEquipPmTrailsEndPointEntry 9 }

genEquipPmTrailsEndPointActivePathCounts	OBJECT-TYPE
        SYNTAX		INTEGER
        ACCESS  	read-only
        STATUS 		mandatory
        DESCRIPTION
		"Active path seconds. "
		::= { genEquipPmTrailsEndPointEntry 10 }

genEquipPmTrailsEndPointIDF  OBJECT-TYPE
		SYNTAX  Integrity
        ACCESS  read-only
        STATUS mandatory
        DESCRIPTION
		"This value indicates if the IDF (Invalid Data Flag), was set."
        ::= { genEquipPmTrailsEndPointEntry 11 }

genEquipPMStatistics	OBJECT IDENTIFIER ::= {genEquipPM 4}

genEquipRMONResetCounters  OBJECT-TYPE
		SYNTAX  OffOn
        ACCESS  read-write
        STATUS 	mandatory
        DESCRIPTION
		"Clear all Ethernet RMON counters."
        ::= { genEquipPMStatistics 1 }

		
-- Radio Configuration
genEquipRadio	OBJECT IDENTIFIER ::= {genEquip 7}

-- Radio Status Table
genEquipRadioStatusTable  OBJECT-TYPE
        SYNTAX  SEQUENCE OF GenEquipRadioStatusEntry
        ACCESS  not-accessible
        STATUS mandatory
        DESCRIPTION
        "Radio status table"
        ::= { genEquipRadio 1 }

genEquipRadioStatusEntry OBJECT-TYPE
        SYNTAX GenEquipRadioStatusEntry
        ACCESS not-accessible
        STATUS mandatory
          DESCRIPTION
          "Radio status table"
        INDEX { genEquipRadioStatusRadioId }
        ::= { genEquipRadioStatusTable 1 }

GenEquipRadioStatusEntry ::=
		SEQUENCE {
			genEquipRadioStatusRadioId
				RadioId,
			genEquipRadioStatusMSE 
            	INTEGER,
			genEquipRadioStatusDefectedBlocks 
            	INTEGER,
			genEquipRadioStatusBER 
				BerLevel,
			genEquipRadioStatusXPI
				INTEGER,
			genEquipRadioStatusXPICEnabled
				EnableDisableSMI2
}

genEquipRadioStatusRadioId	OBJECT-TYPE
        SYNTAX		RadioId 
        ACCESS  	read-only
        STATUS 		mandatory
        DESCRIPTION
		"This value is the radio ID that serves as the table Index."
		::= { genEquipRadioStatusEntry 1 }

genEquipRadioStatusMSE	OBJECT-TYPE
        SYNTAX		INTEGER
        ACCESS  	read-only
        STATUS 		mandatory
        DESCRIPTION
		"MSE (Mean Square Error) of the Rx signal (measured in dB * 100).
		-9900 value (-99.00 dB) means that the signal is not locked.
		~ -3500 value (-35.00 dB) is a good MSE." 
		::= { genEquipRadioStatusEntry 2 }

genEquipRadioStatusDefectedBlocks	OBJECT-TYPE
        SYNTAX		INTEGER
        ACCESS  	read-only
        STATUS 		mandatory
        DESCRIPTION
		"The number defected radio blocks."
		::= { genEquipRadioStatusEntry 3 }

genEquipRadioStatusBER	OBJECT-TYPE
        SYNTAX		BerLevel
        ACCESS  	read-only
        STATUS 		mandatory
        DESCRIPTION
		"The current radio BER (Bit Error Rate)."
		::= { genEquipRadioStatusEntry 4 }

genEquipRadioStatusXPI	OBJECT-TYPE
        SYNTAX		INTEGER
        ACCESS  	read-only
        STATUS 		mandatory
        DESCRIPTION
		"XPI (Cross Polar Interference) level detected."
		::= { genEquipRadioStatusEntry 5 } 
		
genEquipRadioStatusXPICEnabled	OBJECT-TYPE
        SYNTAX		EnableDisableSMI2
        ACCESS  	read-only
        STATUS 		mandatory
        DESCRIPTION
		"This parameter indicates whether an XPIC script is currently loaded."
		::= { genEquipRadioStatusEntry 6 }

-- Radio Cfg table
genEquipRadioCfgTable  OBJECT-TYPE
        SYNTAX  SEQUENCE OF GenEquipRadioCfgEntry
        ACCESS  not-accessible
        STATUS mandatory
        DESCRIPTION
        "Radio Configuration table."
        ::= { genEquipRadio 2 }

genEquipRadioCfgEntry OBJECT-TYPE
        SYNTAX GenEquipRadioCfgEntry
        ACCESS not-accessible
        STATUS mandatory
          DESCRIPTION
          "Radio Configuration table."
        INDEX { genEquipRadioCfgRadioId }
        ::= { genEquipRadioCfgTable 1 }

GenEquipRadioCfgEntry ::=
		SEQUENCE {
			genEquipRadioCfgRadioId
				RadioId,
			genEquipRadioCfgLinkID 
            	INTEGER,
			genEquipRadioCfgMACHeaderCompression 
            	EnableDisable,
			genEquipRadioCfgClearCounters 
            	OffOn,
			genEquipRadioCfgIfLoopback 
            	LoopbackType,
			genEquipRadioCfgExcessiveBERThreshold 
				BerLevel,
			genEquipRadioCfgSignalDegradeThreshold 
				SignalLevel,
			genEquipRadioCfgRadioAdmin 
            	EnableDisable,
			genEquipRadioCfgRadioOperationalStatus 
            	DownUp,
			genEquipRadioCfgRadioTrafficPriorityScheme
				INTEGER,
			genEquipRadioCfgRadioHiPriorityEthernetBW
				INTEGER,
			genEquipRadioCfgRadioMultiRadioEnable
				EnableDisable,
			genEquipRadioCfgRadioMultiRadioBlockLocalTraffic
				INTEGER,
			genEquipRadioCfgRadioMultiRadioBlockMateTraffic
				INTEGER,
			genEquipRadioCfgRadioCurrentAvailableCapacity
				INTEGER,
			genEquipRadioCfgRadioMultiRadioExcessiveBERAdmin
				EnableDisable,
			genEquipRadioCfgRadioMultiRadioSignalDegradeAdmin
				EnableDisable,
			genEquipRadioCfgEnAlarmGenOnRslDegrade
				EnableDisable,
			genEquipRadioCfgAlarmGenRslNominalLevel
				INTEGER,
			genEquipRadioCfgAlarmGenRslDegradationMargin
				INTEGER,
			genEquipRadioCfgLinkShutDownOnRadioFailure
				EnableDisable
}               

genEquipRadioCfgRadioId	OBJECT-TYPE
        SYNTAX		RadioId 
        ACCESS  	read-only
        STATUS 		mandatory
        DESCRIPTION
		"This value is the radio ID that serves as this table Index"
		::= { genEquipRadioCfgEntry 1 }

genEquipRadioCfgLinkID	OBJECT-TYPE
        SYNTAX		INTEGER (1..65535)
        ACCESS  	read-write
        STATUS 		mandatory
        DESCRIPTION
		"Radio configuration link ID"
		::= { genEquipRadioCfgEntry 2 }


genEquipRadioCfgMACHeaderCompression	OBJECT-TYPE
        SYNTAX		EnableDisable
        ACCESS  	read-write
        STATUS 		mandatory
        DESCRIPTION
		"The Admin state of the MAC header compression."
		::= { genEquipRadioCfgEntry 3 }

genEquipRadioCfgClearCounters	OBJECT-TYPE
        SYNTAX		OffOn
        ACCESS  	read-write
        STATUS 		mandatory
        DESCRIPTION
		"Setting this parameter to ON will clear the radio counters."
		::= { genEquipRadioCfgEntry 4 }

genEquipRadioCfgIfLoopback	OBJECT-TYPE
        SYNTAX		INTEGER {
						off(0),
						towardsSystem(1)
						}
        ACCESS  	read-write
        STATUS 		mandatory
        DESCRIPTION
		"IF loopback."
		::= { genEquipRadioCfgEntry 5 }

genEquipRadioCfgExcessiveBERThreshold	OBJECT-TYPE
        SYNTAX		INTEGER { n1e-3(2), n1e-4(3), n1e-5(4) }
        ACCESS  	read-write
        STATUS 		mandatory
        DESCRIPTION
		"'Excessive BER' PM threshold." 
		::= { genEquipRadioCfgEntry 6 }

genEquipRadioCfgSignalDegradeThreshold	OBJECT-TYPE
        SYNTAX		SignalLevel
        ACCESS  	read-write
        STATUS 		mandatory
        DESCRIPTION
		"'Signal degrade' PM threshold."
		::= { genEquipRadioCfgEntry 7 }

genEquipRadioCfgRadioAdmin	OBJECT-TYPE
        SYNTAX		EnableDisable
        ACCESS  	read-write
        STATUS 		obsolete
        DESCRIPTION
		"Radio Admin state (Enable,Disable) can be used in ifTable::ifAdminStatus"
		::= { genEquipRadioCfgEntry 8 }

genEquipRadioCfgRadioOperationalStatus	OBJECT-TYPE
        SYNTAX		DownUp
        ACCESS  	read-only
        STATUS 		mandatory
        DESCRIPTION
		"Radio Operational status (Up,Down) can be used in ifTable::ifOperStatus"
		::= { genEquipRadioCfgEntry 9 }
            			
genEquipRadioCfgRadioTrafficPriorityScheme	OBJECT-TYPE
        SYNTAX		INTEGER {
						high-tdm-over-ethernet (0),
						high-ethernet-over-tdm (1),
						high-tdm-over-high-ethernet (2)
					}
        ACCESS  	read-write
        STATUS 		mandatory
        DESCRIPTION
		"this parameter configures the relative priority of different traffic streams. 
		High-tdm-over-high-ethernet gives priorities as follows: 
		(1) TDM high priority (2) Ethernet high priority (3) TDM low priority (4) Etherenet low priority. 
		High-Ethernet-over-tdm gives priorities as follows: (1) Ethernet high priority (2) TDM high priority (3) TDM low priority (4) Etherenet low priority. 
		Tdm-over-ethernet gives priorities as follows: (1) TDM high priority (2) TDM low priority (3) Ethernet"
		::= { genEquipRadioCfgEntry 10 }
            			
genEquipRadioCfgRadioHiPriorityEthernetBW	OBJECT-TYPE
        SYNTAX		INTEGER (0..500000)
        ACCESS  	read-write
        STATUS 		mandatory
        DESCRIPTION
		"this parameter configures the amount of bandwith reserved for high-priority Ethernet. 
		It must be a number in resolution of 2.048 Mbit/s for E1 systems or 1.544 Mbit/s for T1 systems. 
		The maximum possible capacity is given by genEquipRadioCfgRadioCurrentAvailableCapacity"
		::= { genEquipRadioCfgEntry 11 }
            			
genEquipRadioCfgRadioMultiRadioEnable	OBJECT-TYPE
        SYNTAX		EnableDisable
        ACCESS  	read-write
        STATUS 		mandatory
        DESCRIPTION
		"this parameter enables/disables the multi-radio feature for this radio. 
		Notice that for the feature to work it must be configured in two adjacent radios (odd and even slots)"
		::= { genEquipRadioCfgEntry 12 }

genEquipRadioCfgRadioMultiRadioBlockLocalTraffic	OBJECT-TYPE
        SYNTAX		INTEGER {
						dont-block (0),
						block-this-radio (1)
						}
        ACCESS  	read-write
        STATUS 		mandatory
        DESCRIPTION
		"this parameter allows stopping distribution of data to different radios in Multi-Radio mode for debugging purposes"
		::= { genEquipRadioCfgEntry 13 }
            			
genEquipRadioCfgRadioMultiRadioBlockMateTraffic	OBJECT-TYPE
        SYNTAX		INTEGER {
						dont-block (0),
						block-this-radio (1)
						}
        ACCESS  	read-write
        STATUS 		mandatory
        DESCRIPTION
		"this parameter allows stopping distribution of data to the radio in the mate IDU in Multi-Radio mode for debugging purposes"
		::= { genEquipRadioCfgEntry 14 }
            			
genEquipRadioCfgRadioCurrentAvailableCapacity	OBJECT-TYPE
        SYNTAX		INTEGER 
        ACCESS  	read-only
        STATUS 		mandatory
        DESCRIPTION
		"This parameter indicates the maximum possible capacity available for Ethernet. 
		This sets a top limit for amount of high-priority Ethernet bandwidth"
		::= { genEquipRadioCfgEntry 15 }
            			
genEquipRadioCfgRadioMultiRadioExcessiveBERAdmin	OBJECT-TYPE
        SYNTAX		EnableDisable 
        ACCESS  	read-write
        STATUS 		mandatory
        DESCRIPTION
		"This parameter configures whether in Multi-Radio mode data stops being distributed to the radio in 
		case of an excessive BER condition"
		::= { genEquipRadioCfgEntry 16 }
            			
genEquipRadioCfgRadioMultiRadioSignalDegradeAdmin	OBJECT-TYPE
        SYNTAX		EnableDisable
        ACCESS  	read-write
        STATUS 		mandatory
        DESCRIPTION
		"This parameter configures whether in Multi-Radio mode data stops being distributed to the radio in 
		case of a signal degraded condition"
		::= { genEquipRadioCfgEntry 17 }

genEquipRadioCfgEnAlarmGenOnRslDegrade	OBJECT-TYPE
        SYNTAX		EnableDisable
        ACCESS  	read-write
        STATUS 		mandatory
        DESCRIPTION
		"TEnable/Disable alarm and trapgeneration on RSL degradationbelow user defined threshold.If enabled, 
		trap and alarm willbe generated when current RSLlevel degrades below userdefined threshold for 5subsequent seconds. 
		Alarm willbe cleared after RSL level staysabove the threshold for at leastanother 5 seconds. 
		Thresholdis calculated as a nominal RSLlevel minus the degradationmargin."
		::= { genEquipRadioCfgEntry 18 }

genEquipRadioCfgAlarmGenRslNominalLevel	OBJECT-TYPE
        SYNTAX		INTEGER (-100..0)
        ACCESS  	read-write
        STATUS 		mandatory
        DESCRIPTION
		"RSL nominal level [in dBm] foralarm and event generation."
		::= { genEquipRadioCfgEntry 19 }

genEquipRadioCfgAlarmGenRslDegradationMargin	OBJECT-TYPE
        SYNTAX		INTEGER (10..30)
        ACCESS  	read-write
        STATUS 		mandatory
        DESCRIPTION
		"RSL degradation margin [in dB]for alarm and eventgeneration. The margin isrelative to the nominal RSLlevel"
		::= { genEquipRadioCfgEntry 20 }

genEquipRadioCfgLinkShutDownOnRadioFailure	OBJECT-TYPE
        SYNTAX		EnableDisable
        ACCESS  	read-write
        STATUS 		mandatory
        DESCRIPTION
		"This parameter enables shutting down the link and initiating automatic 
		state propagation upon a failure in each one of the radios. 
		Radio failure condition is determined by user configurations and can be 
		one of the following: 
		Radio LOF, Link ID mismatch, Radio excessive BER, Radio signal degrade, Link ID mismatch."
		::= { genEquipRadioCfgEntry 21 }

		
-- Remote Radio 
genEquipRemoteRadio	OBJECT IDENTIFIER ::= {genEquipRadio 3}

genEquipRemoteRadioTable  OBJECT-TYPE
        SYNTAX  SEQUENCE OF GenEquipRemoteRadioEntry
        ACCESS  not-accessible
        STATUS mandatory
        DESCRIPTION
        "Remote radio table."
        ::= { genEquipRemoteRadio 1 }

genEquipRemoteRadioEntry OBJECT-TYPE
        SYNTAX GenEquipRemoteRadioEntry
        ACCESS not-accessible
        STATUS mandatory
          DESCRIPTION
          "Remote radio table."
        INDEX { genEquipRemoteRadioRadioId }
        ::= { genEquipRemoteRadioTable 1 }

GenEquipRemoteRadioEntry ::=
		SEQUENCE {
			genEquipRemoteRadioRadioId
				RadioId,
			genEquipRemoteRadioRemoteCommunication 
				DownUp,
			genEquipRemoteRadioRemoteIPAddr 
				IpAddress,
			genEquipRemoteRadioRemoteRxLevel 
				INTEGER,
			genEquipRemoteRadioRemoteForceMaxTxLevel 
				INTEGER,
			genEquipRemoteRadioRemoteTxFreq 
				INTEGER,
			genEquipRemoteRadioRemoteRxFreq 
				INTEGER,
			genEquipRemoteRadioRemoteATPCReferenceRxLevel
				INTEGER,
			genEquipRemoteRadioRemoteFloatingIPAddr
				IpAddress,
			genEquipRemoteRadioRemoteDefaultGateway
				IpAddress,
			genEquipRemoteRadioRemoteMostSevereAlarm
				Severity,
			genEquipRemoteRadioRemoteSubnetMask
				IpAddress,
			genEquipRemoteRadioRemoteSlotID
				INTEGER
}
			
genEquipRemoteRadioRadioId	OBJECT-TYPE
        SYNTAX		RadioId 
        ACCESS  	read-only
        STATUS 		mandatory
        DESCRIPTION
		"This value is the radio ID that serves as this table Index"
		::= { genEquipRemoteRadioEntry 1 }

			
genEquipRemoteRadioRemoteCommunication	OBJECT-TYPE
        SYNTAX		DownUp
        ACCESS  	read-only
        STATUS 		mandatory
        DESCRIPTION
		"The operational status of the remote radio."
		::= { genEquipRemoteRadioEntry 2 }

genEquipRemoteRadioRemoteIPAddr	OBJECT-TYPE
        SYNTAX		IpAddress
        ACCESS  	read-write
        STATUS 		mandatory
        DESCRIPTION
		"The remote Ip address."
		::= { genEquipRemoteRadioEntry 3 }

genEquipRemoteRadioRemoteRxLevel	OBJECT-TYPE
        SYNTAX		INTEGER (-199..0)
        ACCESS  	read-only
        STATUS 		mandatory
        DESCRIPTION
		"The Rx level of the remote radio (in dBm)"
		::= { genEquipRemoteRadioEntry 4 }

genEquipRemoteRadioRemoteForceMaxTxLevel	OBJECT-TYPE
        SYNTAX		INTEGER (-50..34)
        ACCESS  	read-write
        STATUS 		mandatory
        DESCRIPTION
		"Command that forces the remote radio maximum Tx level (in dBm)"
		::= { genEquipRemoteRadioEntry 5 }

genEquipRemoteRadioRemoteTxFreq	OBJECT-TYPE
        SYNTAX		INTEGER
        ACCESS  	read-write
        STATUS 		mandatory
        DESCRIPTION
		"The remote radio Tx frequancy (in MHz)."
		::= { genEquipRemoteRadioEntry 6 }

genEquipRemoteRadioRemoteRxFreq	OBJECT-TYPE
        SYNTAX		INTEGER
        ACCESS  	read-write
        STATUS 		mandatory
        DESCRIPTION
		"The remote radio Rx frequancy (in MHz)."
		::= { genEquipRemoteRadioEntry 7 }
		
genEquipRemoteRadioRemoteATPCReferenceRxLevel	OBJECT-TYPE
        SYNTAX		INTEGER (0..199)
        ACCESS  	read-write
        STATUS 		mandatory
        DESCRIPTION
		"The RSL reference level for the ATPC mechanism in the remote radio."
		::= { genEquipRemoteRadioEntry 8 }       
		
genEquipRemoteRadioRemoteFloatingIPAddr	OBJECT-TYPE
        SYNTAX		IpAddress
        ACCESS  	read-write
        STATUS 		mandatory
        DESCRIPTION
		"This value indicates the floating IP address used in 
		the remote shelf if its main units are in 1+1 protection mode."
		::= { genEquipRemoteRadioEntry 9 }
				
genEquipRemoteRadioRemoteDefaultGateway	OBJECT-TYPE
        SYNTAX		IpAddress
        ACCESS  	read-only
        STATUS 		mandatory
        DESCRIPTION
		"Default gateway of remote NE (Network Element) across this radio link."
		::= { genEquipRemoteRadioEntry 10 }
		
genEquipRemoteRadioRemoteMostSevereAlarm	OBJECT-TYPE
        SYNTAX		Severity
        ACCESS  	read-only
        STATUS 		mandatory
        DESCRIPTION
		"Most severe alarm of remote NE (Network Element) across this radio link."
		::= { genEquipRemoteRadioEntry 11 }			

genEquipRemoteRadioRemoteSubnetMask	OBJECT-TYPE
        SYNTAX		IpAddress
        ACCESS  	read-only
        STATUS 		mandatory
        DESCRIPTION
		"Subnet mask of remote NE (Network Element) across this radio link."
		::= { genEquipRemoteRadioEntry 12 }			
				
genEquipRemoteRadioRemoteSlotID	OBJECT-TYPE
        SYNTAX		INTEGER (1..6)
        ACCESS  	read-only
        STATUS 		mandatory
        DESCRIPTION
		"The remote radio slot number."
		::= { genEquipRemoteRadioEntry 13 }			
				
-- Radio MRMC
genEquipRadioMRMC	OBJECT IDENTIFIER ::= {genEquipRadio 4}

genEquipRadioMRMCTable  OBJECT-TYPE
        SYNTAX  SEQUENCE OF GenEquipRadioMRMCEntry
        ACCESS  not-accessible
        STATUS mandatory
        DESCRIPTION
        "MRMC stauts table (Multi rate multi constellation)"
        ::= { genEquipRadioMRMC 1 }

genEquipRadioMRMCEntry OBJECT-TYPE
        SYNTAX GenEquipRadioMRMCEntry
        ACCESS not-accessible
        STATUS mandatory
          DESCRIPTION
          "MRMC status table (Multi rate multi constellation)"
        INDEX { genEquipRadioMRMCRadioId }
        ::= { genEquipRadioMRMCTable 1 }

GenEquipRadioMRMCEntry ::=
		SEQUENCE {
			genEquipRadioMRMCRadioId
				RadioId,
			genEquipRadioMRMCSelectedScriptIndex 
            	INTEGER,
			genEquipRadioMRMCOccupidBandwidth 
            	INTEGER,
			genEquipRadioMRMCOperMode 
            	INTEGER,
			genEquipRadioMRMCCurrTxProfile 
            	INTEGER,
			genEquipRadioMRMCCurrTxQAM 
            	INTEGER,
			genEquipRadioMRMCCurrTxBitrate 
            	INTEGER,
			genEquipRadioMRMCCurrTxVc 
            	INTEGER,
			genEquipRadioMRMCCurrRxProfile 
            	INTEGER,
			genEquipRadioMRMCCurrRxQAM 
            	INTEGER,
			genEquipRadioMRMCCurrRxBitrate 
            	INTEGER,
			genEquipRadioMRMCCurrRxVc 
            	INTEGER,
            genEquipRadioMRMCCurrGrade
            	INTEGER,
			genEquipRadioMRMCEnAlarmOnAcmProfileDegrade
				EnableDisable,
			genEquipRadioMRMCAlarmOnAcmProfileDegradeThreshold
				INTEGER
}

genEquipRadioMRMCRadioId	OBJECT-TYPE
        SYNTAX		RadioId 
        ACCESS  	read-only
        STATUS 		mandatory
        DESCRIPTION
		"This value is the radio ID that serves as this table Index"
		::= { genEquipRadioMRMCEntry 1 }

genEquipRadioMRMCSelectedScriptIndex	OBJECT-TYPE
        SYNTAX		INTEGER
        ACCESS  	read-write
        STATUS 		mandatory
        DESCRIPTION
		"The index of the MRMC script. The description of the script located in the genEquipRadioMRMCScriptTable."
		::= { genEquipRadioMRMCEntry 2 }

genEquipRadioMRMCOccupidBandwidth	OBJECT-TYPE
        SYNTAX		INTEGER
        ACCESS  	read-only
        STATUS 		mandatory
        DESCRIPTION
		"The Occupid Bandwidth (in KHz)."
		::= { genEquipRadioMRMCEntry 3 }

genEquipRadioMRMCOperMode	OBJECT-TYPE
        SYNTAX		INTEGER {
						regular-mode(0),
						acm-fixed-mode(1),
						acm-adaptive-mode(2)
		}
        ACCESS  	read-only
        STATUS 		mandatory
        DESCRIPTION
		"The Mode of the MRMC script."
		::= { genEquipRadioMRMCEntry 4 }

genEquipRadioMRMCCurrTxProfile	OBJECT-TYPE
        SYNTAX		INTEGER (0..16) 
        ACCESS  	read-only
        STATUS 		mandatory
        DESCRIPTION
		"The Tx profile number."
		::= { genEquipRadioMRMCEntry 5 }

genEquipRadioMRMCCurrTxQAM	OBJECT-TYPE
        SYNTAX		INTEGER (4..1024)
        ACCESS  	read-only
        STATUS 		mandatory
        DESCRIPTION
		"The current Tx QAM (modulation)."
		::= { genEquipRadioMRMCEntry 6 }

genEquipRadioMRMCCurrTxBitrate	OBJECT-TYPE
        SYNTAX		INTEGER (1..1000000) 
        ACCESS  	read-only
        STATUS 		mandatory
        DESCRIPTION
		"The current Tx bit rate (in Kbps)"
		::= { genEquipRadioMRMCEntry 7 }

genEquipRadioMRMCCurrTxVc	OBJECT-TYPE
        SYNTAX		INTEGER
        ACCESS  	read-only
        STATUS 		mandatory
        DESCRIPTION
		"The current number of Tx TDM channels."
		::= { genEquipRadioMRMCEntry 8 }
		
genEquipRadioMRMCCurrRxProfile	OBJECT-TYPE
        SYNTAX		INTEGER (0..16) 
        ACCESS  	read-only
        STATUS 		mandatory
        DESCRIPTION
		"The current Rx profile number"
		::= { genEquipRadioMRMCEntry 9 }

genEquipRadioMRMCCurrRxQAM	OBJECT-TYPE
        SYNTAX		INTEGER (4..1024)
        ACCESS  	read-only
        STATUS 		mandatory
        DESCRIPTION
		"The current Rx QAM (modulation)."
		::= { genEquipRadioMRMCEntry 10 }

genEquipRadioMRMCCurrRxBitrate	OBJECT-TYPE
        SYNTAX		INTEGER (1..1000000) 
        ACCESS  	read-only
        STATUS 		mandatory
        DESCRIPTION
		"The current Rx bit rate (in Kbps)"
		::= { genEquipRadioMRMCEntry 11 }

genEquipRadioMRMCCurrRxVc	OBJECT-TYPE
        SYNTAX		INTEGER
        ACCESS  	read-only
        STATUS 		mandatory
        DESCRIPTION
		"The current number of Rx TDM channels."
		::= { genEquipRadioMRMCEntry 12 }

genEquipRadioMRMCCurrGrade  OBJECT-TYPE
        SYNTAX		INTEGER { 
						unknown(0), 
						grade-1(1), 
						grade-2(2), 
						grade-3(3) 
		}
        ACCESS  	read-only
        STATUS 		mandatory
        DESCRIPTION
		"The grade of the current script."
		::= { genEquipRadioMRMCEntry 13 }

genEquipRadioMRMCEnAlarmOnAcmProfileDegrade	OBJECT-TYPE
        SYNTAX		EnableDisable 
        ACCESS  	read-write
        STATUS 		mandatory
        DESCRIPTION
		"Enable/Disable event and trapgeneration on ACM profiledegrade. 
		When enabled and ifcurrent radio script supportsAdaptive Code Modulation(ACM) event and trap will 
		begenerated upon ACM profiledegradation below userdefinedthreshold. 
		Alarm willbe generated only if the ACMprofile stays below thethreshold for at least 5 subsequent seconds. 
		Alarm willbe cleared after ACM profilereturns to be above thethreshold again."
		::= { genEquipRadioMRMCEntry 14 }

genEquipRadioMRMCAlarmOnAcmProfileDegradeThreshold	OBJECT-TYPE
        SYNTAX		INTEGER (1..7)
        ACCESS  	read-write
        STATUS 		mandatory
        DESCRIPTION
		"ACM profile threshold foralarm generation"
		::= { genEquipRadioMRMCEntry 15 }

		

genEquipRadioMRMCScriptTable  OBJECT-TYPE
        SYNTAX  SEQUENCE OF GenEquipRadioMRMCScriptEntry
        ACCESS  not-accessible
        STATUS mandatory
        DESCRIPTION
        "The MRMC script table."
        ::= { genEquipRadioMRMC 2 }

genEquipRadioMRMCScriptEntry OBJECT-TYPE
        SYNTAX GenEquipRadioMRMCScriptEntry
        ACCESS not-accessible
        STATUS mandatory
          DESCRIPTION
          "The MRMC script table."
        INDEX { genEquipRadioMRMCScriptRadioId, genEquipRadioMRMCScriptIndex }
        ::= { genEquipRadioMRMCScriptTable 1 }

GenEquipRadioMRMCScriptEntry ::=
		SEQUENCE {
			genEquipRadioMRMCScriptRadioId
				RadioId,
			genEquipRadioMRMCScriptIndex
				INTEGER,
			genEquipRadioMRMCScriptName 
            	DisplayString,
			genEquipRadioMRMCScriptOperMode
				INTEGER,
			genEquipRadioMRMCScriptProfile
				INTEGER,
			genEquipRadioMRMCScriptProfileBitrate
				INTEGER,
			genEquipRadioMRMCScriptAdaptivePower
				INTEGER,
			genEquipRadioMRMCScriptReference
				INTEGER,
			genEquipRadioMRMCScriptMinProfile
				INTEGER
}

genEquipRadioMRMCScriptRadioId	OBJECT-TYPE
        SYNTAX		RadioId 
        ACCESS  	read-only
        STATUS 		mandatory
        DESCRIPTION
		"This value is the radio ID that serves as this table Index"
		::= { genEquipRadioMRMCScriptEntry 1 }


genEquipRadioMRMCScriptIndex OBJECT-TYPE
        SYNTAX INTEGER
        ACCESS read-only
        STATUS mandatory
        DESCRIPTION
        "The index of the MRMC scripts."
        ::= { genEquipRadioMRMCScriptEntry 2 }
		
genEquipRadioMRMCScriptName OBJECT-TYPE
        SYNTAX DisplayString
        ACCESS read-only
        STATUS mandatory
        DESCRIPTION
        "The MRMC script name."
        ::= { genEquipRadioMRMCScriptEntry 3 }
		
genEquipRadioMRMCScriptOperMode OBJECT-TYPE
        SYNTAX		INTEGER {
						regular-mode(0),
						acm-fixed-mode(1),
						acm-adaptive-mode(2)
		}
		ACCESS read-only
        STATUS mandatory
        DESCRIPTION
        "The script operational mode."
        ::= { genEquipRadioMRMCScriptEntry 4 }
		
genEquipRadioMRMCScriptProfile OBJECT-TYPE
        SYNTAX INTEGER {
					profile-0(0),
					profile-1(1),
					profile-2(2),
					profile-3(3),
					profile-4(4),
					profile-5(5),
					profile-6(6),
					profile-7(7),
					profile-8(8),
					profile-9(9),
					profile-10(10),
					profile-11(11),
					profile-12(12),
					profile-13(13),
					profile-14(14),
					profile-15(15)
		}
        ACCESS read-only
        STATUS mandatory
        DESCRIPTION
        "The profile number of the script"
        ::= { genEquipRadioMRMCScriptEntry 5 }
		
genEquipRadioMRMCScriptProfileBitrate OBJECT-TYPE
        SYNTAX INTEGER (1..1000000) 
        ACCESS read-only
        STATUS mandatory
        DESCRIPTION
        "The Bit rate of the MRMC profile (in Kbps)."
        ::= { genEquipRadioMRMCScriptEntry 6 }
		
genEquipRadioMRMCScriptAdaptivePower OBJECT-TYPE
        SYNTAX INTEGER {
					enable-adaptive-power(0),
					disable-adaptive-power(1)
		}
        ACCESS read-only
        STATUS mandatory
        DESCRIPTION
        "'Adaptive Power' option which is available only when operation mode is ACM-adaptive"
        ::= { genEquipRadioMRMCScriptEntry 7 }
		
		
genEquipRadioMRMCScriptReference OBJECT-TYPE
        SYNTAX INTEGER {
					calss-2(0),
					class-4(1),
					class-5b(2),
					class-6a(3),
					fcc(4)
		}
        ACCESS read-only
        STATUS mandatory
        DESCRIPTION
        "'Reference Class' option which is available only when operation mode 'ACM-adaptive' AND 'Adaptive Power' are enabled."
        ::= { genEquipRadioMRMCScriptEntry 8 }
				
genEquipRadioMRMCScriptMinProfile OBJECT-TYPE
        SYNTAX INTEGER {
					profile-0(0),
					profile-1(1),
					profile-2(2),
					profile-3(3),
					profile-4(4),
					profile-5(5),
					profile-6(6),
					profile-7(7),
					profile-8(8),
					profile-9(9),
					profile-10(10),
					profile-11(11),
					profile-12(12),
					profile-13(13),
					profile-14(14),
					profile-15(15)
		}
        ACCESS read-only
        STATUS mandatory
        DESCRIPTION
        "'Minimum Profile' option which is available only when operation mode 'ACM-adaptive' AND 'Adaptive Power' are enabled.
        It state the minimum profile level for this script."
        ::= { genEquipRadioMRMCScriptEntry 9 }
				
		
-- Services Configuration
genEquipServices	OBJECT IDENTIFIER ::= {genEquip 8}
-- Ethernet Switch
genEquipEthernetSwitch	OBJECT IDENTIFIER ::= {genEquipServices 1}

-- Ethernet Switch configuration
genEquipEthernetSwitchCfg	OBJECT IDENTIFIER ::= {genEquipEthernetSwitch 1}

genEquipEthernetSwitchCfgAppType OBJECT-TYPE
        SYNTAX INTEGER { 	
			single-pipe(1),
			managed-switch(2),
			metro-switch(3)
		}
        ACCESS read-write
        STATUS mandatory
        DESCRIPTION
        "The mode of the switch application. Note, managed-switch or metro-swtich require license.
        Single-pipe: No switching is done, the NE acts as a Pipe.
        Managed-switch: The switch application is configured as IEEE 802.1Q switch.
        Metro-switch: The switch application is configured as IEEE 802.1ad switch."
        ::= { genEquipEthernetSwitchCfg 1 }
		
genEquipEthernetSwitchCfgVIDTable  OBJECT-TYPE
        SYNTAX  SEQUENCE OF GenEquipEthernetSwitchCfgVIDEntry
        ACCESS  not-accessible
        STATUS mandatory
        DESCRIPTION
        "The switch VLAN table."
        ::= { genEquipEthernetSwitchCfg 2 }

genEquipEthernetSwitchCfgVIDEntry OBJECT-TYPE
        SYNTAX GenEquipEthernetSwitchCfgVIDEntry
        ACCESS not-accessible
        STATUS mandatory
          DESCRIPTION
          "The switch VLAN table."
        INDEX { genEquipEthernetSwitchCfgVIDIndex }
        ::= { genEquipEthernetSwitchCfgVIDTable 1 }

GenEquipEthernetSwitchCfgVIDEntry ::=
		SEQUENCE {
			genEquipEthernetSwitchCfgVIDIndex
				INTEGER,
			genEquipEthernetSwitchCfgVIDName
				DisplayString,
			genEquipEthernetSwitchCfgVIDState
				INTEGER,
			genEquipEthernetSwitchCfgVIDMemberPorts
				DisplayString,
			genEquipEthernetSwitchCfgVIDEVCID
				DisplayString,
			genEquipEthernetSwitchCfgVIDEVCDescription
				DisplayString,
			genEquipEthernetSwitchCfgVIDRowStatus
				RowStatus
}

genEquipEthernetSwitchCfgVIDIndex OBJECT-TYPE
        SYNTAX INTEGER  (0..4095)
        ACCESS read-write
        STATUS mandatory
        DESCRIPTION
        "VLAN number, the index of the table."
        ::= { genEquipEthernetSwitchCfgVIDEntry 1 }
		
genEquipEthernetSwitchCfgVIDName OBJECT-TYPE
        SYNTAX DisplayString
        ACCESS read-write
        STATUS mandatory
        DESCRIPTION
        "VLAN name."
        ::= { genEquipEthernetSwitchCfgVIDEntry 2 }
		
genEquipEthernetSwitchCfgVIDState OBJECT-TYPE
        SYNTAX INTEGER {
					suspend(1),
					active(2)
		}
        ACCESS read-write
        STATUS mandatory
        DESCRIPTION
        "VLAN state."
        ::= { genEquipEthernetSwitchCfgVIDEntry 3 }
		
genEquipEthernetSwitchCfgVIDMemberPorts OBJECT-TYPE
        SYNTAX DisplayString
        ACCESS read-write
        STATUS mandatory
        DESCRIPTION
        "A string that indicates in which ports this VLAN is allowed. Port numbers are separated by spaces"
        ::= { genEquipEthernetSwitchCfgVIDEntry 4 }
		
genEquipEthernetSwitchCfgVIDEVCID OBJECT-TYPE
        SYNTAX DisplayString
        ACCESS read-write
        STATUS mandatory
        DESCRIPTION
        "This parameter defines a name for the Ethernet service running over this VLAN. 
		This information is used by the NMS as a service identifier"
        ::= { genEquipEthernetSwitchCfgVIDEntry 5 }
		
genEquipEthernetSwitchCfgVIDEVCDescription OBJECT-TYPE
        SYNTAX DisplayString
        ACCESS read-write
        STATUS mandatory
        DESCRIPTION
        "This parameter allows adding a description for the Ethernet service running over this VLAN. 
		This information is informational only for users purposes"
        ::= { genEquipEthernetSwitchCfgVIDEntry 6 }
		
genEquipEthernetSwitchCfgVIDRowStatus OBJECT-TYPE
        SYNTAX RowStatus -- active(1),notInService(2),notReady(3),createAndGo(4),createAndWait(5),destroy(6)
        ACCESS read-write
        STATUS mandatory
        DESCRIPTION
        "The raw status of the vlan table."
        ::= { genEquipEthernetSwitchCfgVIDEntry 30 }
			
genEquipEthernetSwitchCfgPbbteEthertype  OBJECT-TYPE
        SYNTAX  INTEGER (0..65535)
        ACCESS  read-write
        STATUS mandatory
        DESCRIPTION
        "The PBB-TE-Tag ethertype value"
        ::= { genEquipEthernetSwitchCfg 3 }

genEquipEthernetSwitchCfgProviderEthertype  OBJECT-TYPE
        SYNTAX  INTEGER {
					i0x8100(0),
					i0x88A8(1),
					i0x9100(2),
					i0x9200(3)
		}
        ACCESS  read-write
        STATUS mandatory
        DESCRIPTION
        "Ethertype of the provider VLANS (S-tag). This parameter configures the Marvell switch 
		and it applys for all the ethernet ports. Possible choises are { 0x8100 , 0x9100 , 0x88A8 , 0x9200 }."
        ::= { genEquipEthernetSwitchCfg 4 }


-- Ethernet Switch xSTP
genEquipEthernetSwitchXSTP	OBJECT IDENTIFIER ::= {genEquipEthernetSwitch 2}

genEquipEthernetSwitchXSTPProtocol OBJECT-TYPE
        SYNTAX INTEGER { 
					disable(0), 
					stp(1), 
					rstp(2), 
					ring-rstp(3), 
					mstp(4), 
					ring-mstp(5) 
		}
        ACCESS read-write
        STATUS mandatory
        DESCRIPTION
        "Selection of the xSTP protocol. Note that not all protocols may be available in all software releases"
        ::= { genEquipEthernetSwitchXSTP 1 }

-- Ethernet Switch RSTP family (Ring RSTP or RSTP)
genEquipEthernetSwitchXSTPParams	OBJECT IDENTIFIER ::= {genEquipEthernetSwitchXSTP 2}


genEquipEthernetSwitchXSTPBridgeID OBJECT-TYPE
        SYNTAX DisplayString
        ACCESS read-only
        STATUS mandatory
        DESCRIPTION
        "The RSTP bridge ID"
        ::= { genEquipEthernetSwitchXSTPParams 1 }

genEquipEthernetSwitchXSTPRootID OBJECT-TYPE
        SYNTAX DisplayString
        ACCESS read-only
        STATUS mandatory
        DESCRIPTION
        "The RSTP root id."
        ::= { genEquipEthernetSwitchXSTPParams 2 }

genEquipEthernetSwitchXSTPRootPath OBJECT-TYPE
        SYNTAX INTEGER
        ACCESS read-only
        STATUS mandatory
        DESCRIPTION
        "The RSTP root path cost."
        ::= { genEquipEthernetSwitchXSTPParams 3 }

genEquipEthernetSwitchXSTPBridgeRole OBJECT-TYPE
        SYNTAX INTEGER { 
					root-bridge(0), 
					designated-bridge(1) 
		}
        ACCESS read-only
        STATUS mandatory
        DESCRIPTION
        "The bridge role."
        ::= { genEquipEthernetSwitchXSTPParams 4 }

genEquipEthernetSwitchXSTPCfgPriority OBJECT-TYPE
        SYNTAX INTEGER (0..61440)
        ACCESS read-write
        STATUS mandatory
        DESCRIPTION
        "RSTP Bridge priority."
        ::= { genEquipEthernetSwitchXSTPParams 5 }

genEquipEthernetSwitchXSTPParamsEthernetPortsTable  OBJECT-TYPE
        SYNTAX  SEQUENCE OF GenEquipEthernetSwitchXSTPParamsEthernetPortsEntry
        ACCESS  not-accessible
        STATUS mandatory
        DESCRIPTION
        "RSTP port status table."
        ::= { genEquipEthernetSwitchXSTPParams 6 }

genEquipEthernetSwitchXSTPParamsEthernetPortsEntry OBJECT-TYPE
        SYNTAX GenEquipEthernetSwitchXSTPParamsEthernetPortsEntry
        ACCESS not-accessible
        STATUS mandatory
          DESCRIPTION
          "RSTP port status table."
        INDEX { ifIndex }
        ::= { genEquipEthernetSwitchXSTPParamsEthernetPortsTable 1 }

GenEquipEthernetSwitchXSTPParamsEthernetPortsEntry ::=
		SEQUENCE {
			genEquipEthernetSwitchXSTPParamsEthernetPortsState
            	INTEGER,
			genEquipEthernetSwitchXSTPParamsEthernetPortsRole 
            	INTEGER,
			genEquipEthernetSwitchXSTPParamsEthernetPortsPathCost 
            	INTEGER,
			genEquipEthernetSwitchXSTPParamsEthernetPortsPriority 
            	INTEGER,
			genEquipEthernetSwitchXSTPParamsEthernetDesPathCost
            	INTEGER,
			genEquipEthernetSwitchXSTPParamsEthernetEdgePort
            	NoYes
}

genEquipEthernetSwitchXSTPParamsEthernetPortsState OBJECT-TYPE
        SYNTAX INTEGER { 
				discarding(0),
				listening(1),
				learning(2),
				forwarding(3),
				blocking(4)
		}
        ACCESS read-only
        STATUS mandatory
        DESCRIPTION
        "RSTP port state."
        ::= { genEquipEthernetSwitchXSTPParamsEthernetPortsEntry 1 }
		
genEquipEthernetSwitchXSTPParamsEthernetPortsRole OBJECT-TYPE
        SYNTAX INTEGER { 
				masterport(0),
				alternate(1),
				rootport(2),
				designated(3),
				disabled(4),
				backup(5)
		}
        ACCESS read-only
        STATUS mandatory
        DESCRIPTION
        "RSTP port role."
        ::= { genEquipEthernetSwitchXSTPParamsEthernetPortsEntry 2 }
		
genEquipEthernetSwitchXSTPParamsEthernetPortsPathCost OBJECT-TYPE
        SYNTAX INTEGER (1..200000000)
        ACCESS read-write
        STATUS mandatory
        DESCRIPTION
        "RSTP configured path cost."
        ::= { genEquipEthernetSwitchXSTPParamsEthernetPortsEntry 3 }
		
genEquipEthernetSwitchXSTPParamsEthernetPortsPriority OBJECT-TYPE
        SYNTAX INTEGER (0..240)
        ACCESS read-write
        STATUS mandatory
        DESCRIPTION
        "RSTP configured port priority."
        ::= { genEquipEthernetSwitchXSTPParamsEthernetPortsEntry 4 }
		
genEquipEthernetSwitchXSTPParamsEthernetDesPathCost OBJECT-TYPE
        SYNTAX INTEGER
        ACCESS read-only
        STATUS mandatory
        DESCRIPTION
        "RSTP designated path cost. This is the path cost to the root port from this local port."
        ::= { genEquipEthernetSwitchXSTPParamsEthernetPortsEntry 5 }
		
genEquipEthernetSwitchXSTPParamsEthernetEdgePort OBJECT-TYPE
        SYNTAX NoYes
        ACCESS read-write
        STATUS mandatory
        DESCRIPTION
        "This parameter indicates if the port is an Edge port or not."
        ::= { genEquipEthernetSwitchXSTPParamsEthernetPortsEntry 6 }




-- Ethernet Switch QoS & Rate Limiting
genEquipEthernetSwitchQoS	OBJECT IDENTIFIER ::= {genEquipEthernetSwitch 3}

genEquipEthernetSwitchQoSTable  OBJECT-TYPE
        SYNTAX  SEQUENCE OF GenEquipEthernetSwitchQoSEntry
        ACCESS  not-accessible
        STATUS mandatory
        DESCRIPTION
        "The switch application, QoS Table."
        ::= { genEquipEthernetSwitchQoS 1 }

genEquipEthernetSwitchQoSEntry OBJECT-TYPE
        SYNTAX GenEquipEthernetSwitchQoSEntry
        ACCESS not-accessible
        STATUS mandatory
        DESCRIPTION
          "The switch application, QoS Table, per Ethernet port based on ifIndex."
        INDEX { ifIndex }
        ::= { genEquipEthernetSwitchQoSTable 1 }

GenEquipEthernetSwitchQoSEntry ::=
		SEQUENCE {
			genEquipEthernetSwitchQoSFirstCrit 
            	INTEGER,
			genEquipEthernetSwitchQoSSecondCrit 
            	INTEGER,
			genEquipEthernetSwitchQoSThirdCrit 
            	INTEGER,
			genEquipEthernetSwitchQoSDefClassification 
            	INTEGER,
			genEquipEthernetSwitchQoSEgressSched
            	INTEGER,
			genEquipEthernetSwitchQoSEgressShaper
            	OffOn,
			genEquipEthernetSwitchQoSEgressShaperRate
            	INTEGER,
			genEquipEthernetSwitchQoSIngressPolicer 
            	DisplayString
}

genEquipEthernetSwitchQoSFirstCrit OBJECT-TYPE
        SYNTAX INTEGER { 
					disable(0),
					queueDecision(1),
					pbitOverride(2),
					queueAndPbitOverride(3)
		}
        ACCESS read-write
        STATUS mandatory
        DESCRIPTION
        "First classification criteria. This is the first criteria which will be evaluated for incoming frames.
	   queueDecision causes classification by defined static MAC address.
	   pbitOverride causes classification by pbits.
	   queueAndPbitOverridecauses classification by defined static MAC address, and changes the pbits accordingly."
        ::= { genEquipEthernetSwitchQoSEntry 1 }
		
genEquipEthernetSwitchQoSSecondCrit OBJECT-TYPE
        SYNTAX INTEGER { 
					disable(0),
					queueDecision(1),
					pbitOverride(2),
					queueAndPbitOverride(3)
		}
        ACCESS read-write
        STATUS mandatory
        DESCRIPTION
       "Second classification criteria. Applicable if match with first criteria is not found.
	  queueDecision causes classification by defined VLAN to queue mapping.
	  pbitOverride causes classification by pbits.
	  queueAndPbitOverrideclassification by defined VLAN to queue mapping, and changes the pbits accordingly."

        ::= { genEquipEthernetSwitchQoSEntry 2 }
		
genEquipEthernetSwitchQoSThirdCrit OBJECT-TYPE
        SYNTAX INTEGER {
					ipTosPriority(0),
					vlanPbitspriority(1),
					ipTosOverVlanPbitsPriority(2),
					vlanPbitsOverIpTosPriority(3),
					portPriority(4)
		}
        ACCESS read-write
        STATUS mandatory
        DESCRIPTION
        "Third classification criteria. Applicable if match with first or second criteria is not found.
	  ipTosPriority causes classification by defined IP TOS to queue mapping only.
	  vlanPbitspriority causes classification by pbits only.
	  ipTosOverVlanPbitsPriority causes classification by IP TOS and then by pbits .
	  ipTosOverVlanPbitsPriority causes classification by pbits and then by IP TOS.
	  portPriority causes port-based classification according to port priority."
        ::= { genEquipEthernetSwitchQoSEntry 3 }
		
genEquipEthernetSwitchQoSDefClassification OBJECT-TYPE
        SYNTAX INTEGER { 
					first(0),
					second(1),
					third(2),
					fourth(3)
		}
        ACCESS read-write
        STATUS mandatory
        DESCRIPTION
        "Default classification for frame that does suit to the previous classifications. 
        Choosing first will classify this frame as the first criteria for example."
        ::= { genEquipEthernetSwitchQoSEntry 4 }
		
genEquipEthernetSwitchQoSEgressSched OBJECT-TYPE
        SYNTAX INTEGER { 
				allQueuesStrict(0),
				fourthQueueStrict(1),
				fourthThirdQueuesStrict(2),
				allQueuesHrr(3)
		}
        ACCESS read-write
        STATUS mandatory
        DESCRIPTION
        "Egress scheduler options."
        ::= { genEquipEthernetSwitchQoSEntry 5 }
		
genEquipEthernetSwitchQoSEgressShaper OBJECT-TYPE
        SYNTAX OffOn
        ACCESS read-write
        STATUS mandatory
        DESCRIPTION
        "Enable/Disable egress shaping."
        ::= { genEquipEthernetSwitchQoSEntry 6 }
		
genEquipEthernetSwitchQoSEgressShaperRate OBJECT-TYPE
        SYNTAX INTEGER (64..1000000)
        ACCESS read-write
        STATUS mandatory
        DESCRIPTION
        "Egress shaper rate."
        ::= { genEquipEthernetSwitchQoSEntry 7 }
		
genEquipEthernetSwitchQoSIngressPolicer OBJECT-TYPE
        SYNTAX DisplayString
        ACCESS read-write
        STATUS mandatory
        DESCRIPTION
        "Ingress policer (rate limiting) name assiciated with this port. 
        The policer Name is defined in genEquipEthernetSwitchQoSPolicerNameName (in a table)"
        ::= { genEquipEthernetSwitchQoSEntry 8 }


-- VLAN Pbit Remap table
genEquipEthernetSwitchVlanPbitRemapTable  OBJECT-TYPE
        SYNTAX  SEQUENCE OF GenEquipEthernetSwitchVlanPbitRemapEntry
        ACCESS  not-accessible
        STATUS mandatory
        DESCRIPTION
        "VLAN priority bits remapping table."
        ::= { genEquipEthernetSwitchQoS 2 }

genEquipEthernetSwitchVlanPbitRemapEntry OBJECT-TYPE
        SYNTAX GenEquipEthernetSwitchVlanPbitRemapEntry
        ACCESS not-accessible
        STATUS mandatory
          DESCRIPTION
          "VLAN priority bits remap table."
        INDEX { ifIndex, genEquipEthernetSwitchVlanPbitRemapPbit }
        ::= { genEquipEthernetSwitchVlanPbitRemapTable 1 }

GenEquipEthernetSwitchVlanPbitRemapEntry ::=
		SEQUENCE {
			genEquipEthernetSwitchVlanPbitRemapPbit 
            	INTEGER,
			genEquipEthernetSwitchVlanPbitRemapRemappedPbit 
            	INTEGER
}

genEquipEthernetSwitchVlanPbitRemapPbit OBJECT-TYPE
        SYNTAX INTEGER 
        ACCESS read-only
        STATUS mandatory
        DESCRIPTION
        "The ingress Pbit."
        ::= { genEquipEthernetSwitchVlanPbitRemapEntry 1 }
		
genEquipEthernetSwitchVlanPbitRemapRemappedPbit OBJECT-TYPE
        SYNTAX INTEGER 
        ACCESS read-write
        STATUS mandatory
        DESCRIPTION
        "The remapped Pbit."
        ::= { genEquipEthernetSwitchVlanPbitRemapEntry 2 }
		
-- VLAN Id Queue
genEquipEthernetSwitchQoSVLANIdToQueueTable  OBJECT-TYPE
        SYNTAX  SEQUENCE OF GenEquipEthernetSwitchQoSVLANIdToQueueEntry
        ACCESS  not-accessible
        STATUS mandatory
        DESCRIPTION
        "VLAN Id to Queue mapping table."
        ::= { genEquipEthernetSwitchQoS 3 }

genEquipEthernetSwitchQoSVLANIdToQueueEntry OBJECT-TYPE
        SYNTAX GenEquipEthernetSwitchQoSVLANIdToQueueEntry
        ACCESS not-accessible
        STATUS mandatory
          DESCRIPTION
          "VLAN Id to Queue mapping table."
        INDEX { genEquipEthernetSwitchCfgVIDIndex }  -- list of all defined vlans (vlan index)
        ::= { genEquipEthernetSwitchQoSVLANIdToQueueTable 1 }

GenEquipEthernetSwitchQoSVLANIdToQueueEntry ::=
		SEQUENCE {
			genEquipEthernetSwitchQoSVLANIdToQueueQueue 
            	QueueName
}

		
genEquipEthernetSwitchQoSVLANIdToQueueQueue OBJECT-TYPE
        SYNTAX QueueName
        ACCESS read-write
        STATUS mandatory
        DESCRIPTION
        "Queue for the vlan."
        ::= { genEquipEthernetSwitchQoSVLANIdToQueueEntry 1 }
		

-- LAG Defenitions
genEquipEthernetSwitchLag	OBJECT IDENTIFIER ::= {genEquipEthernetSwitch 4}

genEquipEthernetSwitchLagDistFunction OBJECT-TYPE
        SYNTAX INTEGER  {
				simple-xor(0),
				hash(1)
		}
        ACCESS read-write
        STATUS mandatory
        DESCRIPTION
        "LAG distribution function. "
        ::= { genEquipEthernetSwitchLag 1 }
		
genEquipEthernetSwitchLagMaxNumber OBJECT-TYPE
        SYNTAX INTEGER 
        ACCESS read-only
        STATUS mandatory
        DESCRIPTION
        "Max number of LAG port groups."
        ::= { genEquipEthernetSwitchLag 2 }
		
		
-- Traffic Managment Defenitions
genEquipEthernetSwitchETM	OBJECT IDENTIFIER ::= {genEquipEthernetSwitch 5}

genEquipEthernetSwitchEtmAdmin OBJECT-TYPE
        SYNTAX EnableDisable 
        ACCESS read-write
        STATUS mandatory
        DESCRIPTION
        "Enabling/Disabling the entire enhanced TM functionality."
        ::= { genEquipEthernetSwitchETM 1 }

genEquipEthernetSwitchEtmPTPOptimizedTransportModeAdmin OBJECT-TYPE
        SYNTAX EnableDisable 
        ACCESS read-write
        STATUS mandatory
        DESCRIPTION
        "Precision Time Protocol low PDV channel admin  Upon enabling all the packets classified to the 8th 
		queue will bypass the scheduler and will be sent directly to the Radio Frame. 
		Enabling this parameter will fail if Wayside is enabled."
        ::= { genEquipEthernetSwitchETM 2 }

genEquipEthernetSwitchEtmCountersClear OBJECT-TYPE
        SYNTAX OffOn 
        ACCESS read-write
        STATUS mandatory
        DESCRIPTION
        "Reset selected module's counters."
        ::= { genEquipEthernetSwitchETM 3 }

-- TM Packet classification tables and control parameters. 
genEquipEthernetSwitchEtmClassifier	OBJECT IDENTIFIER ::= {genEquipEthernetSwitchETM 6}

-- TM CoS classification by destination MAC address. 
genEquipEthernetSwitchEtmClassifierByMac	OBJECT IDENTIFIER ::= {genEquipEthernetSwitchEtmClassifier 1}

genEquipEthernetSwitchEtmClassifierByMacAdmin OBJECT-TYPE
        SYNTAX EnableDisable 
        ACCESS read-write
        STATUS mandatory
        DESCRIPTION
        "Enabling/Disabling CoS and color classification by destination MAC addresses."
        ::= { genEquipEthernetSwitchEtmClassifierByMac 1 }

genEquipEthernetSwitchEtmClassifierByMacTable  OBJECT-TYPE
        SYNTAX  SEQUENCE OF GenEquipEthernetSwitchEtmClassifierByMacEntry
        ACCESS  not-accessible             
        STATUS mandatory
        DESCRIPTION
        "Table for CoS and color classification by destination MAC address."
        ::= { genEquipEthernetSwitchEtmClassifierByMac 2 }

genEquipEthernetSwitchEtmClassifierByMacEntry OBJECT-TYPE
        SYNTAX GenEquipEthernetSwitchEtmClassifierByMacEntry
        ACCESS not-accessible
        STATUS mandatory
          DESCRIPTION
          "Table for CoS and color classification by destination MAC address."
        INDEX { genEquipEthernetSwitchEtmClassifierByMacIndex }
        ::= { genEquipEthernetSwitchEtmClassifierByMacTable 1 }

GenEquipEthernetSwitchEtmClassifierByMacEntry ::=
		SEQUENCE {
			genEquipEthernetSwitchEtmClassifierByMacIndex 
            	INTEGER,
			genEquipEthernetSwitchEtmClassifierByMacValue 
            	OCTET STRING,
			genEquipEthernetSwitchEtmClassifierByMacCos
				INTEGER,
			genEquipEthernetSwitchEtmClassifierByMacColor
				GreenYellow,
			genEquipEthernetSwitchEtmClassifierByMacRowStatus
				RowStatus
		}

genEquipEthernetSwitchEtmClassifierByMacIndex OBJECT-TYPE
        SYNTAX INTEGER (1..16)
        ACCESS read-only
        STATUS mandatory
        DESCRIPTION
        "The index is pointing to a table entry. Each entry contains different MAC address."
        ::= { genEquipEthernetSwitchEtmClassifierByMacEntry 1 }

genEquipEthernetSwitchEtmClassifierByMacValue OBJECT-TYPE
		SYNTAX OCTET STRING (SIZE(0..6))
        ACCESS read-write
        STATUS mandatory
        DESCRIPTION
        "MAC Address value for CoS Classification by MAC Table Entry."
        ::= { genEquipEthernetSwitchEtmClassifierByMacEntry 2 }
		
genEquipEthernetSwitchEtmClassifierByMacCos OBJECT-TYPE
		SYNTAX INTEGER (0..7)
        ACCESS read-write
        STATUS mandatory
        DESCRIPTION
        "CoS value for CoS Classification by MAC Table Entry."
        ::= { genEquipEthernetSwitchEtmClassifierByMacEntry 3 }
		
genEquipEthernetSwitchEtmClassifierByMacColor OBJECT-TYPE
		SYNTAX GreenYellow
        ACCESS read-write
        STATUS mandatory
        DESCRIPTION
        "Color value for CoS Classification by MAC Table Entry."
        ::= { genEquipEthernetSwitchEtmClassifierByMacEntry 4 }
		
genEquipEthernetSwitchEtmClassifierByMacRowStatus OBJECT-TYPE
		SYNTAX RowStatus
        ACCESS read-write
        STATUS mandatory
        DESCRIPTION
        "Row Status for this table."
        ::= { genEquipEthernetSwitchEtmClassifierByMacEntry 30 }
		

-- TM CoS classification by UDP port. 
genEquipEthernetSwitchEtmClassifierByUdpPort	OBJECT IDENTIFIER ::= {genEquipEthernetSwitchEtmClassifier 2}

genEquipEthernetSwitchEtmClassifierByUdpPortAdmin OBJECT-TYPE
        SYNTAX EnableDisable 
        ACCESS read-write
        STATUS mandatory
        DESCRIPTION
        "Enabling/Disabling CoS and color classification by UDP source and/or destination ports."
        ::= { genEquipEthernetSwitchEtmClassifierByUdpPort 1 }

genEquipEthernetSwitchEtmClassifierByUdpPortTable  OBJECT-TYPE
        SYNTAX  SEQUENCE OF GenEquipEthernetSwitchEtmClassifierByUdpPortEntry
        ACCESS  not-accessible             
        STATUS mandatory
        DESCRIPTION
        "Table for CoS and color classification by UDP ports. Classification may be based on source port, 
		dest port ,or both - use validity parameter."
        ::= { genEquipEthernetSwitchEtmClassifierByUdpPort 2 }

genEquipEthernetSwitchEtmClassifierByUdpPortEntry OBJECT-TYPE
        SYNTAX GenEquipEthernetSwitchEtmClassifierByUdpPortEntry
        ACCESS not-accessible
        STATUS mandatory
          DESCRIPTION
        "Entry for CoS and color classification by UDP ports. Classification may be based on source port, 
		dest port ,or both - use validity parameter."
        INDEX { genEquipEthernetSwitchEtmClassifierByUdpPortIndex }
        ::= { genEquipEthernetSwitchEtmClassifierByUdpPortTable 1 }

GenEquipEthernetSwitchEtmClassifierByUdpPortEntry ::=
		SEQUENCE {
			genEquipEthernetSwitchEtmClassifierByUdpPortIndex 
            	INTEGER,
			genEquipEthernetSwitchEtmClassifierByUdpPortSrcPort 
            	INTEGER,
			genEquipEthernetSwitchEtmClassifierByUdpPortDestPort
				INTEGER,
			genEquipEthernetSwitchEtmClassifierByUdpPortCos
				INTEGER,
			genEquipEthernetSwitchEtmClassifierByUdpPortColor
				GreenYellow,
			genEquipEthernetSwitchEtmClassifierByUdpPortValidity
				INTEGER,
			genEquipEthernetSwitchEtmClassifierByUdpPortRowStatus
				RowStatus
}

genEquipEthernetSwitchEtmClassifierByUdpPortIndex OBJECT-TYPE
        SYNTAX INTEGER (1..8)
        ACCESS read-only
        STATUS mandatory
        DESCRIPTION
        "The index is pointing to a table entry. Each entry contains different UDP source and destination ports."
        ::= { genEquipEthernetSwitchEtmClassifierByUdpPortEntry 1 }

genEquipEthernetSwitchEtmClassifierByUdpPortSrcPort OBJECT-TYPE
		SYNTAX INTEGER
        ACCESS read-write
        STATUS mandatory
        DESCRIPTION
        "UDP source port value for CoS Classification by UDP ports Table Entry."
        ::= { genEquipEthernetSwitchEtmClassifierByUdpPortEntry 2 }
		
genEquipEthernetSwitchEtmClassifierByUdpPortDestPort OBJECT-TYPE
		SYNTAX INTEGER
        ACCESS read-write
        STATUS mandatory
        DESCRIPTION
        "UDP dest. port value for CoS Classification by UDP ports Table Entry."
        ::= { genEquipEthernetSwitchEtmClassifierByUdpPortEntry 3 }
		
genEquipEthernetSwitchEtmClassifierByUdpPortCos OBJECT-TYPE
		SYNTAX INTEGER (0..7)
        ACCESS read-write
        STATUS mandatory
        DESCRIPTION
        "CoS value for CoS Classification by UDP Ports Table Entry."
        ::= { genEquipEthernetSwitchEtmClassifierByUdpPortEntry 4 }
		
genEquipEthernetSwitchEtmClassifierByUdpPortColor OBJECT-TYPE
		SYNTAX GreenYellow
        ACCESS read-write
        STATUS mandatory
        DESCRIPTION
        "Color value for CoS Classification by UDP ports Table Entry."
        ::= { genEquipEthernetSwitchEtmClassifierByUdpPortEntry 5 }
		
genEquipEthernetSwitchEtmClassifierByUdpPortValidity OBJECT-TYPE
		SYNTAX INTEGER {
					unused(0), 
					src(1), 
					dest(2), 
					both(3)
		}
        ACCESS read-write
        STATUS mandatory
        DESCRIPTION
        "Validity value for CoS Classification by UDP ports Table Entry."
        ::= { genEquipEthernetSwitchEtmClassifierByUdpPortEntry 6 }
		
genEquipEthernetSwitchEtmClassifierByUdpPortRowStatus OBJECT-TYPE
		SYNTAX RowStatus
        ACCESS read-write
        STATUS mandatory
        DESCRIPTION
        "Row Status for this table."
        ::= { genEquipEthernetSwitchEtmClassifierByUdpPortEntry 30 }		

-- TM CoS classification by Ethertypes.
-- genEquipEthernetSwitchEtmClassifierByEthertypes	OBJECT IDENTIFIER ::= {genEquipEthernetSwitchEtmClassifier 3}
-- 
-- genEquipEthernetSwitchEtmClassifierByEthertypesAdmin OBJECT-TYPE
--         SYNTAX EnableDisable 
--         ACCESS read-write
--         STATUS mandatory
--         DESCRIPTION
--         "Enabling/Disabling CoS and color classification by Ethertypes."
--         ::= { genEquipEthernetSwitchEtmClassifierByEthertypes 1 }
-- 
-- genEquipEthernetSwitchEtmClassifierByEthertypesTable  OBJECT-TYPE
--         SYNTAX  SEQUENCE OF GenEquipEthernetSwitchEtmClassifierByEthertypesEntry
--         ACCESS  not-accessible             
--         STATUS mandatory
--         DESCRIPTION
--         "Table for CoS and color classification by Ethertype."
--         ::= { genEquipEthernetSwitchEtmClassifierByEthertypes 2 }
-- 
-- genEquipEthernetSwitchEtmClassifierByEthertypesEntry OBJECT-TYPE
--         SYNTAX GenEquipEthernetSwitchEtmClassifierByEthertypesEntry
--         ACCESS not-accessible
--         STATUS mandatory
--           DESCRIPTION
--           "Table entry for CoS and color classification by Ethertype."
--         INDEX { genEquipEthernetSwitchEtmClassifierByEthertypesIndex }
--         ::= { genEquipEthernetSwitchEtmClassifierByEthertypesTable 1 }
-- 
-- GenEquipEthernetSwitchEtmClassifierByEthertypesEntry ::=
-- 		SEQUENCE {
-- 			genEquipEthernetSwitchEtmClassifierByEthertypesIndex 
--             	INTEGER,
-- 			genEquipEthernetSwitchEtmClassifierByEthertypesValue 
--             	INTEGER,
-- 			genEquipEthernetSwitchEtmClassifierByEthertypesCos
-- 				INTEGER,
-- 			genEquipEthernetSwitchEtmClassifierByEthertypesColor
-- 				GreenYellow,
-- 			genEquipEthernetSwitchEtmClassifierByEthertypesRowStatus
-- 				RowStatus
-- }
-- 
-- genEquipEthernetSwitchEtmClassifierByEthertypesIndex OBJECT-TYPE
--         SYNTAX INTEGER (1..16)
--         ACCESS read-only
--         STATUS mandatory
--         DESCRIPTION
--         "The index is pointing to a table entry. Each entry contains different Ethertype value."
--         ::= { genEquipEthernetSwitchEtmClassifierByEthertypesEntry 1 }
-- 
-- genEquipEthernetSwitchEtmClassifierByEthertypesValue OBJECT-TYPE
-- 		SYNTAX INTEGER
--         ACCESS read-write
--         STATUS mandatory
--         DESCRIPTION
--         "Ethertype tag value for CoS Classification by Ethertype Table Entry."
--         ::= { genEquipEthernetSwitchEtmClassifierByEthertypesEntry 2 }
-- 		
-- genEquipEthernetSwitchEtmClassifierByEthertypesCos OBJECT-TYPE
-- 		SYNTAX INTEGER (0..7)
--         ACCESS read-write
--         STATUS mandatory
--         DESCRIPTION
--         "CoS value for CoS Classification by Ethertype Table Entry."
--         ::= { genEquipEthernetSwitchEtmClassifierByEthertypesEntry 3 }
-- 		
-- genEquipEthernetSwitchEtmClassifierByEthertypesColor OBJECT-TYPE
-- 		SYNTAX GreenYellow
--         ACCESS read-write
--         STATUS mandatory
--         DESCRIPTION
--         "Color value for CoS Classification by Ethertype Table Entry."
--         ::= { genEquipEthernetSwitchEtmClassifierByEthertypesEntry 4 }
-- 		
-- genEquipEthernetSwitchEtmClassifierByEthertypesRowStatus OBJECT-TYPE
-- 		SYNTAX RowStatus
--         ACCESS read-write
--         STATUS mandatory
--         DESCRIPTION
--         "Row Status for this table."
--         ::= { genEquipEthernetSwitchEtmClassifierByEthertypesEntry 30 }
-- 		
-- TM CoS classification by Known PDU MAC addresses. 
genEquipEthernetSwitchEtmClassifierByKnownPduMac	OBJECT IDENTIFIER ::= {genEquipEthernetSwitchEtmClassifier 4}

genEquipEthernetSwitchEtmClassifierByKnownPduMacAdmin OBJECT-TYPE
        SYNTAX EnableDisable 
        ACCESS read-write
        STATUS mandatory
        DESCRIPTION
        "Enabling/Disabling CoS and color classification by known PDU MAC addresses."
        ::= { genEquipEthernetSwitchEtmClassifierByKnownPduMac 1 }

genEquipEthernetSwitchEtmClassifierByKnownPduMacTable  OBJECT-TYPE
        SYNTAX  SEQUENCE OF GenEquipEthernetSwitchEtmClassifierByKnownPduMacEntry
        ACCESS  not-accessible             
        STATUS mandatory
        DESCRIPTION
        "Table for CoS and color classification by known PDU MAC addresses."
        ::= { genEquipEthernetSwitchEtmClassifierByKnownPduMac 2 }

genEquipEthernetSwitchEtmClassifierByKnownPduMacEntry OBJECT-TYPE
        SYNTAX GenEquipEthernetSwitchEtmClassifierByKnownPduMacEntry
        ACCESS not-accessible
        STATUS mandatory
          DESCRIPTION
          "Table entry for CoS and color classification by known PDU MAC addresses."
        INDEX { genEquipEthernetSwitchEtmClassifierByKnownPduMacIndex }
        ::= { genEquipEthernetSwitchEtmClassifierByKnownPduMacTable 1 }

GenEquipEthernetSwitchEtmClassifierByKnownPduMacEntry ::=
		SEQUENCE {
			genEquipEthernetSwitchEtmClassifierByKnownPduMacIndex 
            	INTEGER,
			genEquipEthernetSwitchEtmClassifierByKnownPduMacAddress
				OCTET STRING,
			genEquipEthernetSwitchEtmClassifierByKnownPduMacCos
				INTEGER,
			genEquipEthernetSwitchEtmClassifierByKnownPduMacColor
				GreenYellow,
			genEquipEthernetSwitchEtmClassifierByKnownPduMacValidity
				EnableDisable
		}		

genEquipEthernetSwitchEtmClassifierByKnownPduMacIndex OBJECT-TYPE
        SYNTAX INTEGER (1..66)
        ACCESS read-only
        STATUS mandatory
        DESCRIPTION
        "The index is pointing to a table entry. Each entry contains different PDU MAC address value."
        ::= { genEquipEthernetSwitchEtmClassifierByKnownPduMacEntry 1 }

genEquipEthernetSwitchEtmClassifierByKnownPduMacAddress OBJECT-TYPE
		SYNTAX OCTET STRING (SIZE(6))
        ACCESS read-only
        STATUS mandatory
        DESCRIPTION
        "CoS value for MAC address Classification by known PDU Table Entry."
        ::= { genEquipEthernetSwitchEtmClassifierByKnownPduMacEntry 2 }
 
genEquipEthernetSwitchEtmClassifierByKnownPduMacCos OBJECT-TYPE
		SYNTAX INTEGER (0..7)
        ACCESS read-write
        STATUS mandatory
        DESCRIPTION
        "CoS value for CoS Classification by known PDU Table Entry."
        ::= { genEquipEthernetSwitchEtmClassifierByKnownPduMacEntry 3 }
		
genEquipEthernetSwitchEtmClassifierByKnownPduMacColor OBJECT-TYPE
		SYNTAX GreenYellow
        ACCESS read-write
        STATUS mandatory
        DESCRIPTION
        "Color value for CoS Classification by known PDU Table Entry."
        ::= { genEquipEthernetSwitchEtmClassifierByKnownPduMacEntry 4 }
		
genEquipEthernetSwitchEtmClassifierByKnownPduMacValidity OBJECT-TYPE
		SYNTAX EnableDisable
        ACCESS read-write
        STATUS mandatory
        DESCRIPTION
        "Validity value for Cos Classification by known PDU Table Entry."
        ::= { genEquipEthernetSwitchEtmClassifierByKnownPduMacEntry 5 }

-- TM CoS classification by Flow.
-- genEquipEthernetSwitchEtmClassifierByFlow	OBJECT IDENTIFIER ::= {genEquipEthernetSwitchEtmClassifier 5}
-- 
-- genEquipEthernetSwitchEtmClassifierByFlowAdmin OBJECT-TYPE
--         SYNTAX EnableDisable 
--         ACCESS read-write
--         STATUS mandatory
--         DESCRIPTION
--         "Enabling/Disabling CoS and color classification by flow IDs."
--         ::= { genEquipEthernetSwitchEtmClassifierByFlow 1 }
-- 
-- genEquipEthernetSwitchEtmClassifierByFlowTable  OBJECT-TYPE
--         SYNTAX  SEQUENCE OF GenEquipEthernetSwitchEtmClassifierByFlowEntry
--         ACCESS  not-accessible             
--         STATUS mandatory
--         DESCRIPTION
--         "Table for CoS and color classification by flow-ids."
--         ::= { genEquipEthernetSwitchEtmClassifierByFlow 2 }
-- 
-- genEquipEthernetSwitchEtmClassifierByFlowEntry OBJECT-TYPE
--         SYNTAX GenEquipEthernetSwitchEtmClassifierByFlowEntry
--         ACCESS not-accessible
--         STATUS mandatory
--           DESCRIPTION
--           "Table entry for CoS and color classification by flow-ids."
--         INDEX { genEquipEthernetSwitchEtmClassifierByFlowIndex }
--         ::= { genEquipEthernetSwitchEtmClassifierByFlowTable 1 }
-- 
-- GenEquipEthernetSwitchEtmClassifierByFlowEntry ::=
-- 		SEQUENCE {
-- 			genEquipEthernetSwitchEtmClassifierByFlowIndex 
--             	INTEGER,
-- 			genEquipEthernetSwitchEtmClassifierByFlowCos
-- 				INTEGER,
-- 			genEquipEthernetSwitchEtmClassifierByFlowColor
-- 				GreenYellow,
-- 			genEquipEthernetSwitchEtmClassifierByFlowUsage
-- 				EnableDisable
-- 		}
-- 
-- genEquipEthernetSwitchEtmClassifierByFlowIndex OBJECT-TYPE
--         SYNTAX INTEGER (1..256)
--         ACCESS read-only
--         STATUS mandatory
--         DESCRIPTION
--         "The index is pointing to a table entry. Each entry contains a mapping of flow-id to CoS."
--         ::= { genEquipEthernetSwitchEtmClassifierByFlowEntry 1 }
-- 
-- genEquipEthernetSwitchEtmClassifierByFlowCos OBJECT-TYPE
-- 		SYNTAX INTEGER (0..7)
--         ACCESS read-write
--         STATUS mandatory
--         DESCRIPTION
--         "CoS value for CoS FlowID Mapping Table Entry."
--         ::= { genEquipEthernetSwitchEtmClassifierByFlowEntry 2 }
-- 		
-- genEquipEthernetSwitchEtmClassifierByFlowColor OBJECT-TYPE
-- 		SYNTAX GreenYellow
--         ACCESS read-write
--         STATUS mandatory
--         DESCRIPTION
--         "Color value for CoS FlowId Mapping Table Entry."
--         ::= { genEquipEthernetSwitchEtmClassifierByFlowEntry 3 }
-- 		
-- genEquipEthernetSwitchEtmClassifierByFlowUsage OBJECT-TYPE
-- 		SYNTAX EnableDisable
--         ACCESS read-write
--         STATUS mandatory
--         DESCRIPTION
--         "Validity value for CoS FlowID Mapping Table Entry."
--         ::= { genEquipEthernetSwitchEtmClassifierByFlowEntry 4 }
-- 		
-- TM CoS classification by VLAN P-bits. 
genEquipEthernetSwitchEtmClassifierByVlanPbits	OBJECT IDENTIFIER ::= {genEquipEthernetSwitchEtmClassifier 6}

genEquipEthernetSwitchEtmClassifierByVlanPbitsAdmin OBJECT-TYPE
        SYNTAX EnableDisable 
        ACCESS read-write
        STATUS mandatory
        DESCRIPTION
        "Enabling/Disabling CoS and color classification by VLAN P-bits and CFI/DEI bit."
        ::= { genEquipEthernetSwitchEtmClassifierByVlanPbits 1 }

-- Vlan table
genEquipEthernetSwitchEtmClassifierByVlanPbitsVlanTable  OBJECT-TYPE
        SYNTAX  SEQUENCE OF GenEquipEthernetSwitchEtmClassifierByVlanPbitsVlanEntry
        ACCESS  not-accessible             
        STATUS mandatory
        DESCRIPTION
        "Table for CoS and color classification by VLAN S-tag P-bits and DEI bit."
        ::= { genEquipEthernetSwitchEtmClassifierByVlanPbits 2 }

genEquipEthernetSwitchEtmClassifierByVlanPbitsVlanEntry OBJECT-TYPE
        SYNTAX GenEquipEthernetSwitchEtmClassifierByVlanPbitsVlanEntry
        ACCESS not-accessible
        STATUS mandatory
          DESCRIPTION
          "Table entry for CoS and color classification by VLAN S-tag P-bits and DEI bit."
        INDEX { genEquipEthernetSwitchEtmClassifierByVlanPbitsVlanIndex }
        ::= { genEquipEthernetSwitchEtmClassifierByVlanPbitsVlanTable 1 }

GenEquipEthernetSwitchEtmClassifierByVlanPbitsVlanEntry ::=
		SEQUENCE {
			genEquipEthernetSwitchEtmClassifierByVlanPbitsVlanIndex 
            	INTEGER,
			genEquipEthernetSwitchEtmClassifierByVlanPbitsVlanPriority 
            	INTEGER,
			genEquipEthernetSwitchEtmClassifierByVlanPbitsVlanDei
				INTEGER,
			genEquipEthernetSwitchEtmClassifierByVlanPbitsVlanCos
				INTEGER,
			genEquipEthernetSwitchEtmClassifierByVlanPbitsVlanColor
				GreenYellow
		}

genEquipEthernetSwitchEtmClassifierByVlanPbitsVlanIndex OBJECT-TYPE
        SYNTAX INTEGER 
        ACCESS read-only
        STATUS mandatory
        DESCRIPTION
        "Pbit vlan index to table."
        ::= { genEquipEthernetSwitchEtmClassifierByVlanPbitsVlanEntry 1 }

genEquipEthernetSwitchEtmClassifierByVlanPbitsVlanPriority OBJECT-TYPE
        SYNTAX INTEGER (0..7)
        ACCESS read-only
        STATUS mandatory
        DESCRIPTION
        "Pbit value for regular classification prioritization."
        ::= { genEquipEthernetSwitchEtmClassifierByVlanPbitsVlanEntry 2 }

genEquipEthernetSwitchEtmClassifierByVlanPbitsVlanDei OBJECT-TYPE
        SYNTAX INTEGER (0..1)
        ACCESS read-only
        STATUS mandatory
        DESCRIPTION
        "DEI value for regular classification prioritization by S-tag vlan."
        ::= { genEquipEthernetSwitchEtmClassifierByVlanPbitsVlanEntry 3 }

genEquipEthernetSwitchEtmClassifierByVlanPbitsVlanCos OBJECT-TYPE
		SYNTAX INTEGER (0..7)
        ACCESS read-write
        STATUS mandatory
        DESCRIPTION
        "CoS value for regular classification prioritization by S-tag VLAN."
        ::= { genEquipEthernetSwitchEtmClassifierByVlanPbitsVlanEntry 4 }
		
genEquipEthernetSwitchEtmClassifierByVlanPbitsVlanColor OBJECT-TYPE
		SYNTAX GreenYellow
        ACCESS read-write
        STATUS mandatory
        DESCRIPTION
        "Color value for regular classification prioritization by S-tag VLAN."
        ::= { genEquipEthernetSwitchEtmClassifierByVlanPbitsVlanEntry 5 }
		
-- TM CoS classification by IP DSCP bits. 
genEquipEthernetSwitchEtmClassifierByDscp	OBJECT IDENTIFIER ::= {genEquipEthernetSwitchEtmClassifier 7}

genEquipEthernetSwitchEtmClassifierByDscpAdmin OBJECT-TYPE
        SYNTAX EnableDisable 
        ACCESS read-write
        STATUS mandatory
        DESCRIPTION
        "Enabling/Disabling Cos and color classification by DSCP/TOS bits."
        ::= { genEquipEthernetSwitchEtmClassifierByDscp 1 }

genEquipEthernetSwitchEtmClassifierByDscpTable  OBJECT-TYPE
        SYNTAX  SEQUENCE OF GenEquipEthernetSwitchEtmClassifierByDscpEntry
        ACCESS  not-accessible             
        STATUS mandatory
        DESCRIPTION
        "Table for CoS and color classification by DSCP/TOS bits."
        ::= { genEquipEthernetSwitchEtmClassifierByDscp 2 }

genEquipEthernetSwitchEtmClassifierByDscpEntry OBJECT-TYPE
        SYNTAX GenEquipEthernetSwitchEtmClassifierByDscpEntry
        ACCESS not-accessible
        STATUS mandatory
          DESCRIPTION
          "Table entry for CoS and color classification by DSCP/TOS bits."
        INDEX { genEquipEthernetSwitchEtmClassifierByDscpValue }
        ::= { genEquipEthernetSwitchEtmClassifierByDscpTable 1 }

GenEquipEthernetSwitchEtmClassifierByDscpEntry ::=
		SEQUENCE {
			genEquipEthernetSwitchEtmClassifierByDscpValue 
            	INTEGER,
			genEquipEthernetSwitchEtmClassifierByDscpCos
				INTEGER,
			genEquipEthernetSwitchEtmClassifierByDscpColor
				GreenYellow
		}

genEquipEthernetSwitchEtmClassifierByDscpValue OBJECT-TYPE
        SYNTAX INTEGER (0..63)
        ACCESS read-only
        STATUS mandatory
        DESCRIPTION
        "The index is pointing to a table entry. Each entry contains different DSCP/TOS bits mapping."
        ::= { genEquipEthernetSwitchEtmClassifierByDscpEntry 1 }

genEquipEthernetSwitchEtmClassifierByDscpCos OBJECT-TYPE
		SYNTAX INTEGER (0..7)
        ACCESS read-write
        STATUS mandatory
        DESCRIPTION
        "CoS value for regular classification prioritization by DSCP-tag."
        ::= { genEquipEthernetSwitchEtmClassifierByDscpEntry 2 }
		
genEquipEthernetSwitchEtmClassifierByDscpColor OBJECT-TYPE
		SYNTAX GreenYellow
        ACCESS read-write
        STATUS mandatory
        DESCRIPTION
        "Color value for regular classification prioritization by MPLS."
        ::= { genEquipEthernetSwitchEtmClassifierByDscpEntry 3 }

-- TM CoS classification by MPLS experimental bits. 
genEquipEthernetSwitchEtmClassifierByMplsExp	OBJECT IDENTIFIER ::= {genEquipEthernetSwitchEtmClassifier 8}

genEquipEthernetSwitchEtmClassifierByMplsExpAdmin OBJECT-TYPE
        SYNTAX EnableDisable 
        ACCESS read-write
        STATUS mandatory
        DESCRIPTION
        "Enabling/Disabling CoS and color classification by MPLS experimantal bits."
        ::= { genEquipEthernetSwitchEtmClassifierByMplsExp 1 }

genEquipEthernetSwitchEtmClassifierByMplsExpTable  OBJECT-TYPE
        SYNTAX  SEQUENCE OF GenEquipEthernetSwitchEtmClassifierByMplsExpEntry
        ACCESS  not-accessible             
        STATUS mandatory
        DESCRIPTION
        "Table for CoS and color classification by MPLS experimental bits."
        ::= { genEquipEthernetSwitchEtmClassifierByMplsExp 2 }

genEquipEthernetSwitchEtmClassifierByMplsExpEntry OBJECT-TYPE
        SYNTAX GenEquipEthernetSwitchEtmClassifierByMplsExpEntry
        ACCESS not-accessible
        STATUS mandatory
          DESCRIPTION
          "Table entry for CoS and color classification by MPLS experimental bits."
        INDEX { genEquipEthernetSwitchEtmClassifierByMplsExpValue }
        ::= { genEquipEthernetSwitchEtmClassifierByMplsExpTable 1 }

GenEquipEthernetSwitchEtmClassifierByMplsExpEntry ::=
		SEQUENCE {
			genEquipEthernetSwitchEtmClassifierByMplsExpValue 
            	INTEGER,
			genEquipEthernetSwitchEtmClassifierByMplsExpCos
				INTEGER,
			genEquipEthernetSwitchEtmClassifierByMplsExpColor
				GreenYellow
		}

genEquipEthernetSwitchEtmClassifierByMplsExpValue OBJECT-TYPE
        SYNTAX INTEGER (0..7)
        ACCESS read-only
        STATUS mandatory
        DESCRIPTION
        "The index is pointing to a table entry. Each entry contains different MPLS experimantal bits mapping."
        ::= { genEquipEthernetSwitchEtmClassifierByMplsExpEntry 1 }

genEquipEthernetSwitchEtmClassifierByMplsExpCos OBJECT-TYPE
		SYNTAX INTEGER (0..7)
        ACCESS read-write
        STATUS mandatory
        DESCRIPTION
        "value for regular classification prioritization by MPLS."
        ::= { genEquipEthernetSwitchEtmClassifierByMplsExpEntry 2 }
		
genEquipEthernetSwitchEtmClassifierByMplsExpColor OBJECT-TYPE
		SYNTAX GreenYellow
        ACCESS read-write
        STATUS mandatory
        DESCRIPTION
        "Color value for regular classification prioritization by MPLS."
        ::= { genEquipEthernetSwitchEtmClassifierByMplsExpEntry 3 }

-- TM CoS default color defs. 
genEquipEthernetSwitchEtmClassifierByDefaultCosColor	OBJECT IDENTIFIER ::= {genEquipEthernetSwitchEtmClassifier 9}

genEquipEthernetSwitchEtmClassifierByDefaultCos OBJECT-TYPE
        SYNTAX INTEGER (0..7)
        ACCESS read-write
        STATUS mandatory
        DESCRIPTION
        "CoS value for regular classification prioritization by default port."
        ::= { genEquipEthernetSwitchEtmClassifierByDefaultCosColor 1 }

genEquipEthernetSwitchEtmClassifierByDefaultColor OBJECT-TYPE
        SYNTAX GreenYellow 
        ACCESS read-write
        STATUS mandatory
        DESCRIPTION
        "Table for regular priority by default port mapping table."
        ::= { genEquipEthernetSwitchEtmClassifierByDefaultCosColor 2 }

-- TM CoS classification by Cos To Queue
genEquipEthernetSwitchEtmClassifierByCosToQueue	OBJECT IDENTIFIER ::= {genEquipEthernetSwitchEtmClassifier 10}

genEquipEthernetSwitchEtmClassifierByCosToQueueTable  OBJECT-TYPE
        SYNTAX  SEQUENCE OF GenEquipEthernetSwitchEtmClassifierByCosToQueueEntry
        ACCESS  not-accessible             
        STATUS mandatory
        DESCRIPTION
        "Table for VLAN to FlowId mapping ."
        ::= { genEquipEthernetSwitchEtmClassifierByCosToQueue 1 }

genEquipEthernetSwitchEtmClassifierByCosToQueueEntry OBJECT-TYPE
        SYNTAX GenEquipEthernetSwitchEtmClassifierByCosToQueueEntry
        ACCESS not-accessible
        STATUS mandatory
          DESCRIPTION
          "Table for VLAN to FlowId mapping ."
        INDEX { genEquipEthernetSwitchEtmClassifierByCosToQueueIndex }
        ::= { genEquipEthernetSwitchEtmClassifierByCosToQueueTable 1 }

GenEquipEthernetSwitchEtmClassifierByCosToQueueEntry ::=
		SEQUENCE {
			genEquipEthernetSwitchEtmClassifierByCosToQueueIndex 
            	INTEGER,
			genEquipEthernetSwitchEtmClassifierByCosToQueueCos 
            	INTEGER,
			genEquipEthernetSwitchEtmClassifierByCosToQueueValue
				INTEGER
		}

genEquipEthernetSwitchEtmClassifierByCosToQueueIndex OBJECT-TYPE
        SYNTAX INTEGER
        ACCESS read-only
        STATUS mandatory
        DESCRIPTION
        "The index is pointing to a table entry. Each entry contains a mapping of a different CoS to a queue."
        ::= { genEquipEthernetSwitchEtmClassifierByCosToQueueEntry 1 }

genEquipEthernetSwitchEtmClassifierByCosToQueueCos OBJECT-TYPE
        SYNTAX INTEGER (0..7)
        ACCESS read-only
        STATUS mandatory
        DESCRIPTION
        "The Class of Service value, the mapping of a different CoS to a queue."
        ::= { genEquipEthernetSwitchEtmClassifierByCosToQueueEntry 2 }

genEquipEthernetSwitchEtmClassifierByCosToQueueValue OBJECT-TYPE
		SYNTAX INTEGER (1..8)
        ACCESS read-write
        STATUS mandatory
        DESCRIPTION
        "Queue index for CoS to Queue Mapping Table Entry."
        ::= { genEquipEthernetSwitchEtmClassifierByCosToQueueEntry 3 }
		
-- TM CoS classification by Flows
-- genEquipEthernetSwitchEtmClassifierByFlows	OBJECT IDENTIFIER ::= {genEquipEthernetSwitchEtmClassifier 11}
-- 
-- genEquipEthernetSwitchEtmClassifierByFlowsVlanidToFlowTable  OBJECT-TYPE
--         SYNTAX  SEQUENCE OF GenEquipEthernetSwitchEtmClassifierByFlowsVlanidToFlowEntry
--         ACCESS  not-accessible             
--         STATUS mandatory
--         DESCRIPTION
--         "Table for VLAN to FlowId mapping  ."
--         ::= { genEquipEthernetSwitchEtmClassifierByFlows 1 }
-- 
-- genEquipEthernetSwitchEtmClassifierByFlowsVlanidToFlowEntry OBJECT-TYPE
--         SYNTAX GenEquipEthernetSwitchEtmClassifierByFlowsVlanidToFlowEntry
--         ACCESS not-accessible
--         STATUS mandatory
--           DESCRIPTION
--           "Table entry for VLAN to FlowId mapping  ."
--         INDEX { genEquipEthernetSwitchEtmClassifierByFlowsVlanidToFlowIndex }
--         ::= { genEquipEthernetSwitchEtmClassifierByFlowsVlanidToFlowTable 1 }
-- 
-- GenEquipEthernetSwitchEtmClassifierByFlowsVlanidToFlowEntry ::=
-- 		SEQUENCE {
-- 			genEquipEthernetSwitchEtmClassifierByFlowsVlanidToFlowIndex 
--             	INTEGER,
-- 			genEquipEthernetSwitchEtmClassifierByFlowsVlanidToFlowValue
-- 				INTEGER,
-- 			genEquipEthernetSwitchEtmClassifierByFlowsVlanidToFlowAcmDropLevel
-- 				INTEGER
-- 		}
-- 
-- genEquipEthernetSwitchEtmClassifierByFlowsVlanidToFlowIndex OBJECT-TYPE
--         SYNTAX INTEGER (0..4095)
--         ACCESS read-only
--         STATUS mandatory
--         DESCRIPTION
--         "VLAN ID index."
--         ::= { genEquipEthernetSwitchEtmClassifierByFlowsVlanidToFlowEntry 1 }
-- 
-- genEquipEthernetSwitchEtmClassifierByFlowsVlanidToFlowValue OBJECT-TYPE
-- 		SYNTAX INTEGER (1..256)
--         ACCESS read-write
--         STATUS mandatory
--         DESCRIPTION
--         "Flow Id for a certain VLAN."
--         ::= { genEquipEthernetSwitchEtmClassifierByFlowsVlanidToFlowEntry 2 }
-- 		
-- genEquipEthernetSwitchEtmClassifierByFlowsVlanidToFlowAcmDropLevel OBJECT-TYPE
-- 		SYNTAX INTEGER (0..7)
--         ACCESS read-write
--         STATUS mandatory
--         DESCRIPTION
--         "Flow Id for a certain VLAN."
--         ::= { genEquipEthernetSwitchEtmClassifierByFlowsVlanidToFlowEntry 3 }
-- 
-- Defaults		
-- genEquipEthernetSwitchEtmClassifierByFlowsDefault	OBJECT IDENTIFIER ::= {genEquipEthernetSwitchEtmClassifierByFlows 2}
-- 
-- genEquipEthernetSwitchEtmClassifierByFlowDefaultUntaggedAdmin OBJECT-TYPE
-- 		SYNTAX EnableDisable
--         ACCESS read-write
--         STATUS mandatory
--         DESCRIPTION
--         "Enabling/Disabling default Flow id classification for untagged packets."
--         ::= { genEquipEthernetSwitchEtmClassifierByFlowsDefault 1 }
-- 		
-- genEquipEthernetSwitchEtmClassifierByFlowDefaultUntaggedFlow OBJECT-TYPE
-- 		SYNTAX INTEGER (1..256)
--         ACCESS read-write
--         STATUS mandatory
--         DESCRIPTION
--         "Default Flow id for untagged packets."
--         ::= { genEquipEthernetSwitchEtmClassifierByFlowsDefault 2 }
-- 		
-- genEquipEthernetSwitchEtmClassifierByFlowDefaultIpAdmin OBJECT-TYPE
-- 		SYNTAX EnableDisable
--         ACCESS read-write
--         STATUS mandatory
--         DESCRIPTION
--         "Enabling/Disabling default Flow id classification for ip packets."
--         ::= { genEquipEthernetSwitchEtmClassifierByFlowsDefault 3 }
-- 		
-- genEquipEthernetSwitchEtmClassifierByFlowDefaultIpFlow OBJECT-TYPE
-- 		SYNTAX INTEGER (1..256)
--         ACCESS read-write
--         STATUS mandatory
--         DESCRIPTION
--         "Default Flow id for ip packets."
--         ::= { genEquipEthernetSwitchEtmClassifierByFlowsDefault 4 }
-- 		
-- genEquipEthernetSwitchEtmClassifierByFlowDefaultMplsAdmin OBJECT-TYPE
-- 		SYNTAX EnableDisable
--         ACCESS read-write
--         STATUS mandatory
--         DESCRIPTION
--         "Enabling/Disabling default Flow id classification for mpls packets."
--         ::= { genEquipEthernetSwitchEtmClassifierByFlowsDefault 5 }
-- 		
-- genEquipEthernetSwitchEtmClassifierByFlowDefaultMplsFlow OBJECT-TYPE
-- 		SYNTAX INTEGER (1..256)
--         ACCESS read-write
--         STATUS mandatory
--         DESCRIPTION
--         "Default Flow id for mpls packets."
--         ::= { genEquipEthernetSwitchEtmClassifierByFlowsDefault 6 }
-- 		
-- genEquipEthernetSwitchEtmClassifierByFlowDefaultFlow OBJECT-TYPE
-- 		SYNTAX INTEGER (1..256)
--         ACCESS read-write
--         STATUS mandatory
--         DESCRIPTION
--         "Default Flow id."
--         ::= { genEquipEthernetSwitchEtmClassifierByFlowsDefault 7 }
-- 		
-- 

-- TM Classifier Inband Managment Qos
-- Cos and Color classification by VLAN-ID. Only a single VLAN-ID value can be specified. 
-- This is configuration should be used for inband management VLAN-ID classification to the high priority queue.
genEquipEthernetSwitchEtmClassifierInbandMgmtQoS	OBJECT IDENTIFIER ::= {genEquipEthernetSwitchEtmClassifier 12}

genEquipEthernetSwitchEtmClassifierInbandMgmtAdmin OBJECT-TYPE
 		SYNTAX EnableDisable
        ACCESS read-write
        STATUS mandatory
        DESCRIPTION
        "Enabling/Disabling CoS and Color classification by VLAN ID."
        ::= { genEquipEthernetSwitchEtmClassifierInbandMgmtQoS 1 }
 		
genEquipEthernetSwitchEtmClassifierInbandMgmtVlanId OBJECT-TYPE
 		SYNTAX INTEGER (0..4090)
         ACCESS read-write
         STATUS mandatory
         DESCRIPTION
         "Inband Management vlan id. This parameter should be the same as genEquipEthernetSwitchEtmClassifierInbandMgmtVlanId."
         ::= { genEquipEthernetSwitchEtmClassifierInbandMgmtQoS 2 }
 		
genEquipEthernetSwitchEtmClassifierInbandMgmtCos OBJECT-TYPE
 		SYNTAX INTEGER (0..7)
         ACCESS read-write
         STATUS mandatory
         DESCRIPTION
         "Class of Service. Allowed values: [0-7]."
         ::= { genEquipEthernetSwitchEtmClassifierInbandMgmtQoS 3 }

genEquipEthernetSwitchEtmClassifierInbandMgmtColor OBJECT-TYPE
 		SYNTAX GreenYellow
         ACCESS read-write
         STATUS mandatory
         DESCRIPTION
         "Color 1=green ; 0=yellow."
         ::= { genEquipEthernetSwitchEtmClassifierInbandMgmtQoS 4 }

		 
-- TM ACM drop per queue paramters. 
--genEquipEthernetSwitchEtmAcmDropPerQueue	OBJECT IDENTIFIER ::= {genEquipEthernetSwitchETM 7}

-- TM Policers configuration and mapping tables and parameters 
--genEquipEthernetSwitchEtmPolicers	OBJECT IDENTIFIER ::= {genEquipEthernetSwitchETM 8}

-- TM Queues configuration
genEquipEthernetSwitchEtmQueues	OBJECT IDENTIFIER ::= {genEquipEthernetSwitchETM 9}

genEquipEthernetSwitchEtmQueuesTable  OBJECT-TYPE
        SYNTAX  SEQUENCE OF GenEquipEthernetSwitchEtmQueuesEntry
        ACCESS  not-accessible             
        STATUS mandatory
        DESCRIPTION
        "Table of queue sizes."
        ::= { genEquipEthernetSwitchEtmQueues 1 }

genEquipEthernetSwitchEtmQueuesEntry OBJECT-TYPE
        SYNTAX GenEquipEthernetSwitchEtmQueuesEntry
        ACCESS not-accessible
        STATUS mandatory
          DESCRIPTION
          "Table entry of queue sizes."
        INDEX { genEquipEthernetSwitchEtmQueuesIndex }
        ::= { genEquipEthernetSwitchEtmQueuesTable 1 }

GenEquipEthernetSwitchEtmQueuesEntry ::=
		SEQUENCE {
			genEquipEthernetSwitchEtmQueuesIndex 
            	INTEGER,
			genEquipEthernetSwitchEtmQueuesSize
				INTEGER
		}

genEquipEthernetSwitchEtmQueuesIndex OBJECT-TYPE
        SYNTAX INTEGER (1..8)
        ACCESS read-only
        STATUS mandatory
        DESCRIPTION
        "The Index to a queue."
        ::= { genEquipEthernetSwitchEtmQueuesEntry 1 }

genEquipEthernetSwitchEtmQueuesSize OBJECT-TYPE
		SYNTAX INTEGER {
					kbit-0(0), 
					kbit-500(1),
					kbit-1000(2),
					kbit-2000(3),
					kbit-4000(4)
		}
        ACCESS read-write
        STATUS mandatory
        DESCRIPTION
        "Size of queue[i]"
        ::= { genEquipEthernetSwitchEtmQueuesEntry 2 }
		
-- TM WRED configuration
genEquipEthernetSwitchEtmWred	OBJECT IDENTIFIER ::= {genEquipEthernetSwitchETM 10}

genEquipEthernetSwitchEtmWredAdmin OBJECT-TYPE
        SYNTAX EnableDisable 
        ACCESS read-write
        STATUS mandatory
        DESCRIPTION
        "Enabling/Disabling WRED."
        ::= { genEquipEthernetSwitchEtmWred 1 }


genEquipEthernetSwitchEtmWredThresholdsTable  OBJECT-TYPE
        SYNTAX  SEQUENCE OF GenEquipEthernetSwitchEtmWredThresholdsEntry
        ACCESS  not-accessible             
        STATUS mandatory
        DESCRIPTION
        "WRED thresholds per queue."
        ::= { genEquipEthernetSwitchEtmWred 2 }

genEquipEthernetSwitchEtmWredThresholdsEntry OBJECT-TYPE
        SYNTAX GenEquipEthernetSwitchEtmWredThresholdsEntry
        ACCESS not-accessible
        STATUS mandatory
          DESCRIPTION
          "WRED entry thresholds per queue."
        INDEX { genEquipEthernetSwitchEtmWredQueuesIndex }
        ::= { genEquipEthernetSwitchEtmWredThresholdsTable 1 }

GenEquipEthernetSwitchEtmWredThresholdsEntry ::=
		SEQUENCE {
			genEquipEthernetSwitchEtmWredQueuesIndex 
            	INTEGER,
			genEquipEthernetSwitchEtmWredThresholdsGreenThLow
				INTEGER,
			genEquipEthernetSwitchEtmWredThresholdsGreenThHigh
				INTEGER,
			genEquipEthernetSwitchEtmWredThresholdsYellowThLow
				INTEGER,
			genEquipEthernetSwitchEtmWredThresholdsYellowThHigh
				INTEGER,
			genEquipEthernetSwitchEtmWredThresholdsGreenMaxDrop
				INTEGER,
			genEquipEthernetSwitchEtmWredThresholdsYellowMaxDrop
				INTEGER
		}

genEquipEthernetSwitchEtmWredQueuesIndex OBJECT-TYPE
        SYNTAX INTEGER (1..8)
        ACCESS read-only
        STATUS mandatory
        DESCRIPTION
        "WRED thresholds per queue."
        ::= { genEquipEthernetSwitchEtmWredThresholdsEntry 1 }

genEquipEthernetSwitchEtmWredThresholdsGreenThLow OBJECT-TYPE
		SYNTAX INTEGER (0..4000)
        ACCESS read-write
        STATUS mandatory
        DESCRIPTION
        "WRED green low threshold  defines the queue level (in Kbits) point 
		that the mechanism should start checking if to drop the green frames."
        ::= { genEquipEthernetSwitchEtmWredThresholdsEntry 2 }
		
genEquipEthernetSwitchEtmWredThresholdsGreenThHigh OBJECT-TYPE
		SYNTAX INTEGER (0..4000)
        ACCESS read-write
        STATUS mandatory
        DESCRIPTION
        "WRED green high threshold defines the queue level of occupancy (in Kbits) point that the WRED 
		must drop all arriving green colored frames."
        ::= { genEquipEthernetSwitchEtmWredThresholdsEntry 3 }
		
genEquipEthernetSwitchEtmWredThresholdsYellowThLow OBJECT-TYPE
		SYNTAX INTEGER (0..4000)
        ACCESS read-write
        STATUS mandatory
        DESCRIPTION
        "WRED yellow low threshold  defines the queue level (in Kbits) point that the mechanism should 
		start checking if to drop the yellow frames."
        ::= { genEquipEthernetSwitchEtmWredThresholdsEntry 4 }
		
genEquipEthernetSwitchEtmWredThresholdsYellowThHigh OBJECT-TYPE
		SYNTAX INTEGER (0..4000)
        ACCESS read-write
        STATUS mandatory
        DESCRIPTION
        "WRED yellow high threshold defines the queue level of occupancy (in Kbits) point that the WRED 
		must drop all arriving yellow colored frames."
        ::= { genEquipEthernetSwitchEtmWredThresholdsEntry 5 }
		
genEquipEthernetSwitchEtmWredThresholdsGreenMaxDrop OBJECT-TYPE
		SYNTAX INTEGER (0..100)
        ACCESS read-write
        STATUS mandatory
        DESCRIPTION
        "WRED green max drop threshold  the probability to drop frame at the green high threshold (in percent based units)."
        ::= { genEquipEthernetSwitchEtmWredThresholdsEntry 6 }
		
genEquipEthernetSwitchEtmWredThresholdsYellowMaxDrop OBJECT-TYPE
		SYNTAX INTEGER (0..100)
        ACCESS read-write
        STATUS mandatory
        DESCRIPTION
        "WRED yellow max drop threshold  the probability to drop frame at the yellow high threshold (in percent based units)."
        ::= { genEquipEthernetSwitchEtmWredThresholdsEntry 7 }
		

-- TM Marker configurations
--genEquipEthernetSwitchEtmMarker	OBJECT IDENTIFIER ::= {genEquipEthernetSwitchETM 11}

-- TM Scheduler configuration
genEquipEthernetSwitchEtmScheduler	OBJECT IDENTIFIER ::= {genEquipEthernetSwitchETM 12}

genEquipEthernetSwitchEtmSchedulerQuantum OBJECT-TYPE
        SYNTAX INTEGER
        ACCESS read-write
        STATUS mandatory
        DESCRIPTION
        "WFQ Quantum for credit calculation in bytes (64, 128, 256, 512)."
        ::= { genEquipEthernetSwitchEtmScheduler 1 }


genEquipEthernetSwitchEtmSchedulerConfigTable  OBJECT-TYPE
        SYNTAX  SEQUENCE OF GenEquipEthernetSwitchEtmSchedulerConfigEntry
        ACCESS  not-accessible             
        STATUS mandatory
        DESCRIPTION
        "Table for scheduler configuration: priority and weight for each queue."
        ::= { genEquipEthernetSwitchEtmScheduler 2 }

genEquipEthernetSwitchEtmSchedulerConfigEntry OBJECT-TYPE
        SYNTAX GenEquipEthernetSwitchEtmSchedulerConfigEntry
        ACCESS not-accessible
        STATUS mandatory
        DESCRIPTION
        "Table entry for scheduler configuration: priority and weight for each queue."
        INDEX { genEquipEthernetSwitchEtmSchedulerConfigQueueIndex }
        ::= { genEquipEthernetSwitchEtmSchedulerConfigTable 1 }

GenEquipEthernetSwitchEtmSchedulerConfigEntry ::=
		SEQUENCE {
			genEquipEthernetSwitchEtmSchedulerConfigQueueIndex 
            	INTEGER,
			genEquipEthernetSwitchEtmSchedulerConfigPriority
				INTEGER,
			genEquipEthernetSwitchEtmSchedulerConfigWeight
				INTEGER
		}

genEquipEthernetSwitchEtmSchedulerConfigQueueIndex OBJECT-TYPE
        SYNTAX INTEGER (1..8)
        ACCESS read-only
        STATUS mandatory
        DESCRIPTION
        "queue index."
        ::= { genEquipEthernetSwitchEtmSchedulerConfigEntry 1 }

genEquipEthernetSwitchEtmSchedulerConfigPriority OBJECT-TYPE
		SYNTAX INTEGER (1..4)
        ACCESS read-write
        STATUS mandatory
        DESCRIPTION
        "Strict priority of each queue. 4=highest , 1=lowest."
        ::= { genEquipEthernetSwitchEtmSchedulerConfigEntry 2 }
		
genEquipEthernetSwitchEtmSchedulerConfigWeight OBJECT-TYPE
		SYNTAX INTEGER (0..15)
        ACCESS read-write
        STATUS mandatory
        DESCRIPTION
        "WFQ Weights for each queue"
        ::= { genEquipEthernetSwitchEtmSchedulerConfigEntry 3 }
		
-- TM Egress shaper configuration
genEquipEthernetSwitchEtmShaper	OBJECT IDENTIFIER ::= {genEquipEthernetSwitchETM 13}

genEquipEthernetSwitchEtmShaperGlobalAdmin OBJECT-TYPE
		SYNTAX EnableDisable
        ACCESS read-write
        STATUS mandatory
        DESCRIPTION
        "Global Shaper admin disables/enables the global shaping feature."
        ::= { genEquipEthernetSwitchEtmShaper 1 }

genEquipEthernetSwitchEtmShaperConfigTable  OBJECT-TYPE
        SYNTAX  SEQUENCE OF GenEquipEthernetSwitchEtmShaperConfigEntry
        ACCESS  not-accessible             
        STATUS mandatory
        DESCRIPTION
        "Table of shapers' configurations. Each shaper is on the egress of a queue.."
        ::= { genEquipEthernetSwitchEtmShaper 2 }

genEquipEthernetSwitchEtmShaperConfigEntry OBJECT-TYPE
        SYNTAX GenEquipEthernetSwitchEtmShaperConfigEntry
        ACCESS not-accessible
        STATUS mandatory
        DESCRIPTION
        "Table entry of shapers' configurations. Each shaper is on the egress of a queue.."
        INDEX { genEquipEthernetSwitchEtmShaperConfigIndex }
        ::= { genEquipEthernetSwitchEtmShaperConfigTable 1 }

GenEquipEthernetSwitchEtmShaperConfigEntry ::=
		SEQUENCE {
			genEquipEthernetSwitchEtmShaperConfigIndex 
            	INTEGER,
			genEquipEthernetSwitchEtmShaperConfigAdmin
				INTEGER,
			genEquipEthernetSwitchEtmShaperConfigCir
				INTEGER,
			genEquipEthernetSwitchEtmShaperConfigCbs
				INTEGER,
			genEquipEthernetSwitchEtmShaperConfigLineComp
				INTEGER
		}

genEquipEthernetSwitchEtmShaperConfigIndex OBJECT-TYPE
        SYNTAX INTEGER (1..8)
        ACCESS read-only
        STATUS mandatory
        DESCRIPTION
        "queue index."
        ::= { genEquipEthernetSwitchEtmShaperConfigEntry 1 }

genEquipEthernetSwitchEtmShaperConfigAdmin OBJECT-TYPE
		SYNTAX EnableDisable
        ACCESS read-write
        STATUS mandatory
        DESCRIPTION
        "Egress Shaper admin disables/enables the shaping feature per queue."
        ::= { genEquipEthernetSwitchEtmShaperConfigEntry 2 }
		
genEquipEthernetSwitchEtmShaperConfigCir OBJECT-TYPE
		SYNTAX INTEGER (0..1000000)
        ACCESS read-write
        STATUS mandatory
        DESCRIPTION
        "Egress shaper CIR value - the committed rate as given by the user."
        ::= { genEquipEthernetSwitchEtmShaperConfigEntry 3 }
		
genEquipEthernetSwitchEtmShaperConfigCbs OBJECT-TYPE
		SYNTAX INTEGER (0..128000)
        ACCESS read-write
        STATUS mandatory
        DESCRIPTION
        "Egress shaper committed burst size value."
        ::= { genEquipEthernetSwitchEtmShaperConfigEntry 4 }

genEquipEthernetSwitchEtmShaperConfigLineComp OBJECT-TYPE
		SYNTAX INTEGER (0..255)
        ACCESS read-write
        STATUS mandatory
        DESCRIPTION
        "Egress shaper line compensation value transmitted IFG + Preamble. 
		The shaper adds this value to each arriving frame size."
        ::= { genEquipEthernetSwitchEtmShaperConfigEntry 5 }

-- TM Statistics counters
genEquipEthernetSwitchEtmStatistics	OBJECT IDENTIFIER ::= {genEquipEthernetSwitchETM 14}

genEquipEthernetSwitchEtmStatisticsPortTotalBytesTransmitted OBJECT-TYPE
		SYNTAX INTEGER
        ACCESS read-only
        STATUS mandatory
        DESCRIPTION
        "The number of bytes transmitted via the port (goes into PM)."
        ::= { genEquipEthernetSwitchEtmStatistics 1 }

genEquipEthernetSwitchEtmStatisticsPortTotalUnicastFramesTransmitted OBJECT-TYPE
		SYNTAX INTEGER
        ACCESS read-only
        STATUS mandatory
        DESCRIPTION
        "TThe number of Unicast frames transmitted to the radio port.."
        ::= { genEquipEthernetSwitchEtmStatistics 2 }


genEquipEthernetSwitchEtmStatisticsPortTotalMulticastFramesTransmitted OBJECT-TYPE
		SYNTAX INTEGER
        ACCESS read-only
        STATUS mandatory
        DESCRIPTION
        "The number of Multicast frames transmitted to the radio port.."
        ::= { genEquipEthernetSwitchEtmStatistics 3 }


genEquipEthernetSwitchEtmStatisticsPortTotalBroadcastFramesTransmitted OBJECT-TYPE
		SYNTAX INTEGER
        ACCESS read-only
        STATUS mandatory
        DESCRIPTION
        "The number of Broadcast frames transmitted to the radio port.."
        ::= { genEquipEthernetSwitchEtmStatistics 4 }


genEquipEthernetSwitchEtmStatisticsPortFrames64octTransmitted OBJECT-TYPE
		SYNTAX INTEGER
        ACCESS read-only
        STATUS mandatory
        DESCRIPTION
        "The total number of frames transmitted with a length of exactly 64 Octets."
        ::= { genEquipEthernetSwitchEtmStatistics 5 }


genEquipEthernetSwitchEtmStatisticsPortFrames65to127Transmitted OBJECT-TYPE
		SYNTAX INTEGER
        ACCESS read-only
        STATUS mandatory
        DESCRIPTION
        "The total number of frames transmitted with a length of 65-127 Octets."
        ::= { genEquipEthernetSwitchEtmStatistics 6 }


genEquipEthernetSwitchEtmStatisticsPortFrames128to255Transmitted OBJECT-TYPE
		SYNTAX INTEGER
        ACCESS read-only
        STATUS mandatory
        DESCRIPTION
        "The total number of frames transmitted with a length of 128-255 Octets."
        ::= { genEquipEthernetSwitchEtmStatistics 7 }


genEquipEthernetSwitchEtmStatisticsPortFrames256to511Transmitted OBJECT-TYPE
		SYNTAX INTEGER
        ACCESS read-only
        STATUS mandatory
        DESCRIPTION
        "The total number of frames transmitted with a length of 256-511 Octets)."
        ::= { genEquipEthernetSwitchEtmStatistics 8 }


genEquipEthernetSwitchEtmStatisticsPortFrames512to1023Transmitted OBJECT-TYPE
		SYNTAX INTEGER
        ACCESS read-only
        STATUS mandatory
        DESCRIPTION
        "TThe total number of frames transmitted with a length of 512-1023 Octets."
        ::= { genEquipEthernetSwitchEtmStatistics 9 }


genEquipEthernetSwitchEtmStatisticsPortFrames1024toMtuTransmitted OBJECT-TYPE
		SYNTAX INTEGER
        ACCESS read-only
        STATUS mandatory
        DESCRIPTION
        "The total number of frames transmitted with a length between 1024 and MaxTransmitSize Octets."
        ::= { genEquipEthernetSwitchEtmStatistics 10 }


		
-- IP Pbits to Queue
genEquipEthernetSwitchQoSIPPbits	OBJECT IDENTIFIER ::= {genEquipEthernetSwitchQoS 4}

genEquipEthernetSwitchQoSIPPbitsIPPrio OBJECT-TYPE
        SYNTAX INTEGER { 
			ipPrecedence(0),
			ipv4TOSIPv6(1)  -- diffserv.
		} 
        ACCESS read-write
        STATUS mandatory
        DESCRIPTION
        "IP priority options."
        ::= { genEquipEthernetSwitchQoSIPPbits 1 }
		
genEquipEthernetSwitchQoSIPPbitsTable  OBJECT-TYPE
        SYNTAX  SEQUENCE OF GenEquipEthernetSwitchQoSIPPbitsEntry
        ACCESS  not-accessible             
        STATUS mandatory
        DESCRIPTION
        "Mapping of IP pbits to Queue."
        ::= { genEquipEthernetSwitchQoSIPPbits 2 }

genEquipEthernetSwitchQoSIPPbitsEntry OBJECT-TYPE
        SYNTAX GenEquipEthernetSwitchQoSIPPbitsEntry
        ACCESS not-accessible
        STATUS mandatory
          DESCRIPTION
          "Mapping of IP pbits to Queue."
        INDEX { genEquipEthernetSwitchQoSIPPbitsId }
        ::= { genEquipEthernetSwitchQoSIPPbitsTable 1 }

GenEquipEthernetSwitchQoSIPPbitsEntry ::=
		SEQUENCE {
			genEquipEthernetSwitchQoSIPPbitsId 
            	INTEGER,
			genEquipEthernetSwitchQoSIPPbitsQueue 
            	QueueName
}

genEquipEthernetSwitchQoSIPPbitsId OBJECT-TYPE
        SYNTAX INTEGER 
        ACCESS read-only
        STATUS mandatory
        DESCRIPTION
        "The pbit number."
        ::= { genEquipEthernetSwitchQoSIPPbitsEntry 1 }

genEquipEthernetSwitchQoSIPPbitsQueue OBJECT-TYPE
        SYNTAX QueueName 
        ACCESS read-write
        STATUS mandatory
        DESCRIPTION
        "the queue for that pbit."
        ::= { genEquipEthernetSwitchQoSIPPbitsEntry 2 }
		
		
		
-- VLAN Pbits to queue

genEquipEthernetSwitchQoSVLANPbitsTable  OBJECT-TYPE
        SYNTAX  SEQUENCE OF GenEquipEthernetSwitchQoSVLANPbitsEntry
        ACCESS  not-accessible
        STATUS mandatory
        DESCRIPTION
        "VLAN pbit to queue mapping table."
        ::= { genEquipEthernetSwitchQoS 5 }

genEquipEthernetSwitchQoSVLANPbitsEntry OBJECT-TYPE
        SYNTAX GenEquipEthernetSwitchQoSVLANPbitsEntry
        ACCESS not-accessible
        STATUS mandatory
          DESCRIPTION
          "VLAN pbit to queue mapping table."
        INDEX { genEquipEthernetSwitchQoSVLANPbitsId }
        ::= { genEquipEthernetSwitchQoSVLANPbitsTable 1 }

GenEquipEthernetSwitchQoSVLANPbitsEntry ::=
		SEQUENCE {
			genEquipEthernetSwitchQoSVLANPbitsId 
            	INTEGER,
			genEquipEthernetSwitchQoSVLANPbitsQueue 
            	QueueName
}

genEquipEthernetSwitchQoSVLANPbitsId OBJECT-TYPE
        SYNTAX INTEGER  (1..8)
        ACCESS read-only
        STATUS mandatory
        DESCRIPTION
        "The VLAN'S pbit (index of the table)"
        ::= { genEquipEthernetSwitchQoSVLANPbitsEntry 1 }

genEquipEthernetSwitchQoSVLANPbitsQueue OBJECT-TYPE
        SYNTAX QueueName 
        ACCESS read-write
        STATUS mandatory
        DESCRIPTION
        "The mapped queue for the corresponding VLAN ."
        ::= { genEquipEthernetSwitchQoSVLANPbitsEntry 2 }


-- Queue Weights
genEquipEthernetSwitchQoSQueueWeightsTable  OBJECT-TYPE
        SYNTAX  SEQUENCE OF GenEquipEthernetSwitchQoSQueueWeightsEntry
        ACCESS  not-accessible
        STATUS mandatory
        DESCRIPTION "Queue weights mapping table."
        ::= { genEquipEthernetSwitchQoS 6 }

genEquipEthernetSwitchQoSQueueWeightsEntry OBJECT-TYPE
        SYNTAX GenEquipEthernetSwitchQoSQueueWeightsEntry
        ACCESS not-accessible
        STATUS mandatory
        DESCRIPTION "Queue weights mapping table."
        INDEX { genEquipEthernetSwitchQoSQueueWeightsId }
        ::= { genEquipEthernetSwitchQoSQueueWeightsTable 1 }

GenEquipEthernetSwitchQoSQueueWeightsEntry ::=
		SEQUENCE {
			genEquipEthernetSwitchQoSQueueWeightsId 
            	INTEGER,
			genEquipEthernetSwitchQoSQueueWeightsQueue 
            	QueueName,
			genEquipEthernetSwitchQoSQueueWeightsWeight 
            	INTEGER
}


genEquipEthernetSwitchQoSQueueWeightsId OBJECT-TYPE
        SYNTAX INTEGER (1..4) 
        ACCESS read-only
        STATUS mandatory
        DESCRIPTION
        "Index for this table."
        ::= { genEquipEthernetSwitchQoSQueueWeightsEntry 1 }

genEquipEthernetSwitchQoSQueueWeightsQueue OBJECT-TYPE
        SYNTAX QueueName 
        ACCESS read-only
        STATUS mandatory
        DESCRIPTION
        "The queue number."
        ::= { genEquipEthernetSwitchQoSQueueWeightsEntry 2 }

genEquipEthernetSwitchQoSQueueWeightsWeight OBJECT-TYPE
        SYNTAX INTEGER (1..32)
        ACCESS read-write
        STATUS mandatory
        DESCRIPTION
        "The weight for the queue"
        ::= { genEquipEthernetSwitchQoSQueueWeightsEntry 3 }




-- Policer list
-- Policer Name table
genEquipEthernetSwitchQoSPolicerNameTable  OBJECT-TYPE
        SYNTAX  SEQUENCE OF GenEquipEthernetSwitchQoSPolicerNameEntry
        ACCESS  not-accessible
        STATUS mandatory
        DESCRIPTION
        "Table of configured policers."
        ::= { genEquipEthernetSwitchQoS 7 }

genEquipEthernetSwitchQoSPolicerNameEntry OBJECT-TYPE
        SYNTAX GenEquipEthernetSwitchQoSPolicerNameEntry
        ACCESS not-accessible
        STATUS mandatory
        DESCRIPTION "Table of configured policers."
        INDEX { genEquipEthernetSwitchQoSPolicerNameId }
        ::= { genEquipEthernetSwitchQoSPolicerNameTable 1 }

GenEquipEthernetSwitchQoSPolicerNameEntry ::=
		SEQUENCE {
			genEquipEthernetSwitchQoSPolicerNameId 
            	INTEGER,
			genEquipEthernetSwitchQoSPolicerNameName
            	DisplayString,
			genEquipEthernetSwitchQoSPolicerNameRowStatus
            	RowStatus
}

genEquipEthernetSwitchQoSPolicerNameId OBJECT-TYPE
        SYNTAX INTEGER 
        ACCESS read-only
        STATUS mandatory
        DESCRIPTION
        "Policer ID"
        ::= { genEquipEthernetSwitchQoSPolicerNameEntry 1 }
		
genEquipEthernetSwitchQoSPolicerNameName OBJECT-TYPE
        SYNTAX DisplayString 
        ACCESS read-write
        STATUS mandatory
        DESCRIPTION
        "Policer name."
        ::= { genEquipEthernetSwitchQoSPolicerNameEntry 2 }
				
genEquipEthernetSwitchQoSPolicerNameRowStatus OBJECT-TYPE
        SYNTAX RowStatus 
        ACCESS read-write
        STATUS mandatory
        DESCRIPTION
        "Policer row status."
        ::= { genEquipEthernetSwitchQoSPolicerNameEntry 30 }

-- Policer list table
genEquipEthernetSwitchQoSPolicerListTable  OBJECT-TYPE
        SYNTAX  SEQUENCE OF GenEquipEthernetSwitchQoSPolicerListEntry
        ACCESS  not-accessible
        STATUS mandatory
        DESCRIPTION
        "The policer class table list."
        ::= { genEquipEthernetSwitchQoS 8 }

genEquipEthernetSwitchQoSPolicerListEntry OBJECT-TYPE
        SYNTAX GenEquipEthernetSwitchQoSPolicerListEntry
        ACCESS not-accessible
        STATUS mandatory
          DESCRIPTION
          "The policer class table list."
        INDEX { genEquipEthernetSwitchQoSPolicerNameId, genEquipEthernetSwitchQoSPolicerListId }
        ::= { genEquipEthernetSwitchQoSPolicerListTable 1 }

GenEquipEthernetSwitchQoSPolicerListEntry ::=
		SEQUENCE {
			genEquipEthernetSwitchQoSPolicerListId 
            	INTEGER,
			genEquipEthernetSwitchQoSPolicerListName
				DisplayString,
			genEquipEthernetSwitchQoSPolicerListClassName
            	DisplayString,
			genEquipEthernetSwitchQoSPolicerListTrafficType 
            	INTEGER,
			genEquipEthernetSwitchQoSPolicerListCIR 
            	INTEGER,
			genEquipEthernetSwitchQoSPolicerListCBS 
            	INTEGER,
			genEquipEthernetSwitchQoSPolicerListRowStatus
            	RowStatus
}

genEquipEthernetSwitchQoSPolicerListId OBJECT-TYPE
        SYNTAX INTEGER 
        ACCESS read-only
        STATUS mandatory
        DESCRIPTION
        "The policer ID."
        ::= { genEquipEthernetSwitchQoSPolicerListEntry 1 }
		
genEquipEthernetSwitchQoSPolicerListName OBJECT-TYPE
        SYNTAX DisplayString 
        ACCESS read-write
        STATUS mandatory
        DESCRIPTION
        "The policer class name"
        ::= { genEquipEthernetSwitchQoSPolicerListEntry 2 }

genEquipEthernetSwitchQoSPolicerListClassName OBJECT-TYPE
        SYNTAX DisplayString 
        ACCESS read-write
        STATUS mandatory
        DESCRIPTION
        "The policer class name"
        ::= { genEquipEthernetSwitchQoSPolicerListEntry 3 }
				
genEquipEthernetSwitchQoSPolicerListTrafficType OBJECT-TYPE        
        SYNTAX INTEGER {   
	        unknownUcast(1),
	        unknowMulticast(2), 
	        broadcast(3),
	        multicast(5),
	        unicast(6),
	        arp(8),
	        tcpData(9),
	        tcpControl(10),
	        udp(11),
	        noTcpUdp(12),
	        firstPriority(13),                                                        
	        secondPriority(14),
	        thirdPriority(15),
	        forthPriority(16),
	        allTraffic(17)
        }       
        ACCESS read-write
        STATUS mandatory
        DESCRIPTION
        "The traffic type that the policer applies to."
        ::= { genEquipEthernetSwitchQoSPolicerListEntry 4 }

genEquipEthernetSwitchQoSPolicerListCIR OBJECT-TYPE
        SYNTAX INTEGER 
        ACCESS read-write
        STATUS mandatory
        DESCRIPTION
        "The CIR (Critical Information Rate) value (in Kbps)"
        ::= { genEquipEthernetSwitchQoSPolicerListEntry 5 }

genEquipEthernetSwitchQoSPolicerListCBS OBJECT-TYPE
        SYNTAX INTEGER 
        ACCESS read-write
        STATUS mandatory
        DESCRIPTION
        "The CBS (Critical Burst Size) value (in Bytes)"
        ::= { genEquipEthernetSwitchQoSPolicerListEntry 6 }

genEquipEthernetSwitchQoSPolicerListRowStatus OBJECT-TYPE
        SYNTAX RowStatus 
        ACCESS read-write
        STATUS mandatory
        DESCRIPTION
        "Row status of the table."
        ::= { genEquipEthernetSwitchQoSPolicerListEntry 30 }


-- Static MAC
genEquipEthernetSwitchQoSStaticMacTable  OBJECT-TYPE
        SYNTAX  SEQUENCE OF GenEquipEthernetSwitchQoSStaticMacEntry
        ACCESS  not-accessible
        STATUS mandatory
        DESCRIPTION
        "Static MAC forwarding table."
        ::= { genEquipEthernetSwitchQoS 9 }

genEquipEthernetSwitchQoSStaticMacEntry OBJECT-TYPE
        SYNTAX GenEquipEthernetSwitchQoSStaticMacEntry
        ACCESS not-accessible
        STATUS mandatory
          DESCRIPTION
          "Static MAC forwarding table."
        INDEX { genEquipEthernetSwitchQoSStaticMacId }
        ::= { genEquipEthernetSwitchQoSStaticMacTable 1 }

GenEquipEthernetSwitchQoSStaticMacEntry ::=
		SEQUENCE {
			genEquipEthernetSwitchQoSStaticMacId 
            	INTEGER,
			genEquipEthernetSwitchQoSStaticMacAddr 
            	OCTET STRING,
			genEquipEthernetSwitchQoSStaticMacVlanId
            	INTEGER,
			genEquipEthernetSwitchQoSStaticMacForwardTo 
            	INTEGER,
			genEquipEthernetSwitchQoSStaticMacPriority 
            	INTEGER,
			genEquipEthernetSwitchQoSStaticMacRowStatus
            	RowStatus
}

genEquipEthernetSwitchQoSStaticMacId OBJECT-TYPE
        SYNTAX INTEGER 
        ACCESS read-only
        STATUS mandatory
        DESCRIPTION
        "The index of the table"
        ::= { genEquipEthernetSwitchQoSStaticMacEntry 1 }
		
genEquipEthernetSwitchQoSStaticMacAddr OBJECT-TYPE
		SYNTAX OCTET STRING 
		ACCESS read-write
        STATUS mandatory
        DESCRIPTION
        "Static MAC Address."
        ::= { genEquipEthernetSwitchQoSStaticMacEntry 2 }

genEquipEthernetSwitchQoSStaticMacVlanId OBJECT-TYPE
        SYNTAX INTEGER 
        ACCESS read-write
        STATUS mandatory
        DESCRIPTION
        "VLAN ID for this MAC."
        ::= { genEquipEthernetSwitchQoSStaticMacEntry 3 }
				
genEquipEthernetSwitchQoSStaticMacForwardTo OBJECT-TYPE
        SYNTAX INTEGER 
        ACCESS read-write
        STATUS mandatory
        DESCRIPTION
        "The port number to be forwarded to, starting from 1."
        ::= { genEquipEthernetSwitchQoSStaticMacEntry 4 }

genEquipEthernetSwitchQoSStaticMacPriority OBJECT-TYPE
        SYNTAX INTEGER 
        ACCESS read-write
        STATUS mandatory
        DESCRIPTION
        "The priority to be given to this MAC address."
        ::= { genEquipEthernetSwitchQoSStaticMacEntry 5 }

genEquipEthernetSwitchQoSStaticMacRowStatus OBJECT-TYPE
        SYNTAX RowStatus 
        ACCESS read-write
        STATUS mandatory
        DESCRIPTION
        "The row status of the operation."
        ::= { genEquipEthernetSwitchQoSStaticMacEntry 30 }



		
-- TDM Trails
genEquipTdmTrails	OBJECT IDENTIFIER ::= {genEquipServices 2}

genEquipTdmTrailsTable  OBJECT-TYPE
        SYNTAX  SEQUENCE OF GenEquipTdmTrailsEntry
        ACCESS  not-accessible
        STATUS mandatory
        DESCRIPTION
        "TDM Trails configuration and status table."
        ::= { genEquipTdmTrails 1 }

genEquipTdmTrailsEntry OBJECT-TYPE
        SYNTAX GenEquipTdmTrailsEntry
        ACCESS not-accessible
        STATUS mandatory
          DESCRIPTION
          "TDM Trails PM table."
        INDEX { genEquipTdmTrailID }
        ::= { genEquipTdmTrailsTable 1 }

GenEquipTdmTrailsEntry ::=
		SEQUENCE {
			genEquipTdmTrailID 
            	DisplayString,
			genEquipTdmTrailDescr 
            	DisplayString,
			genEquipTdmTrailProtected 
            	INTEGER,
			genEquipTdmTrailAcmPrio 
            	INTEGER,
			genEquipTdmTrailOperStatus 
            	INTEGER,
			genEquipTdmTrailAlarmStatus
            	INTEGER,
			genEquipTdmTrailSrcSlot
            	INTEGER,
			genEquipTdmTrailSrcType
            	TrailIfType,
			genEquipTdmTrailSrcNum 
            	INTEGER,
			genEquipTdmTrailDest1Slot
            	INTEGER,
			genEquipTdmTrailDest1Type
            	TrailIfType,
			genEquipTdmTrailDest1Num 
            	INTEGER,
			genEquipTdmTrailDest2Slot
            	INTEGER,
			genEquipTdmTrailDest2Type
            	TrailIfType,
			genEquipTdmTrailDest2Num 
            	INTEGER,
			genEquipTdmTrailProtectedForceActive 
            	TrailProtectedType,
			genEquipTdmTrailProtectedActiveTrail
            	TrailProtectedType,
			genEquipTdmTrailProtectedNumOfSwitches
            	INTEGER,
			genEquipTdmTrailPrimaryPathAlarmStatus 
            	INTEGER,
			genEquipTdmTrailSecondaryPathAlarmStatus
            	INTEGER,
			genEquipTdmTrailRowStatus
            	RowStatus
}

genEquipTdmTrailID		OBJECT-TYPE
		SYNTAX 		DisplayString
		ACCESS		read-write
        STATUS		mandatory
        DESCRIPTION
		"The Trail ID. This parameter is the index of the table."
::= { genEquipTdmTrailsEntry 1 }

genEquipTdmTrailDescr		OBJECT-TYPE
		SYNTAX 		DisplayString
		ACCESS		read-write
        STATUS		mandatory
        DESCRIPTION
		"Trail description."
::= { genEquipTdmTrailsEntry 2 }

genEquipTdmTrailProtected		OBJECT-TYPE
		SYNTAX 		INTEGER {
						unProtected(0),
						protected(1),
						protectedAbr(2)
		}
		ACCESS		read-write
        STATUS		mandatory
        DESCRIPTION
		"This parameter indicates whether the trail is protected or not."
::= { genEquipTdmTrailsEntry 3 }

genEquipTdmTrailAcmPrio		OBJECT-TYPE
		SYNTAX 		INTEGER {
						low(0),
						high(1)
		}
		ACCESS		read-write
        STATUS		mandatory
        DESCRIPTION
		"The ACM priority of the trail. In case of High priority TDM trail, ACM is enabled on the link and there is a reduction 
		of the link capacity, this trail will be prioritized before the low priority trails to be dropped."
::= { genEquipTdmTrailsEntry 4 }

genEquipTdmTrailOperStatus		OBJECT-TYPE
		SYNTAX 		INTEGER {
						reserved(0),
						operational(1)
		}
		ACCESS		read-write
        STATUS		mandatory
        DESCRIPTION
		"The status of the TDM trail. in operational case, the trail is active/enabled and send alarms."
::= { genEquipTdmTrailsEntry 5 }

genEquipTdmTrailAlarmStatus		OBJECT-TYPE
		SYNTAX 		INTEGER
		ACCESS		read-only
        STATUS		mandatory
        DESCRIPTION
		"The alarm status of the trail active path.
		The value is a Bit Map: Id-Mismatch(0x01), 
		Excessive-Ber(0x02), Signal-Degrade-Ber(0x04), 
		Invalid-Trail-Status(0x08), Signal-Failure(0x10), RDI-Detected(0x20)."
::= { genEquipTdmTrailsEntry 6 }

genEquipTdmTrailSrcSlot		OBJECT-TYPE
		SYNTAX 		INTEGER
		ACCESS		read-write
        STATUS		mandatory
        DESCRIPTION
		"Trail source slot number."
::= { genEquipTdmTrailsEntry 7 }

genEquipTdmTrailSrcType		OBJECT-TYPE
		SYNTAX 		TrailIfType 
		ACCESS		read-write
        STATUS		mandatory
        DESCRIPTION
		"The type of the source interface of the trail line(0),	radio(1),stm-1-oc-3(2), sync(4)."
::= { genEquipTdmTrailsEntry 8 }

genEquipTdmTrailSrcNum		OBJECT-TYPE
		SYNTAX 		INTEGER
		ACCESS		read-write
        STATUS		mandatory
        DESCRIPTION
		"The interface number, for example E1 number 5. in case of a line."
::= { genEquipTdmTrailsEntry 9 }

genEquipTdmTrailDest1Slot		OBJECT-TYPE
		SYNTAX 		INTEGER
		ACCESS		read-write
        STATUS		mandatory
        DESCRIPTION
		"The slot destination of the trail."
::= { genEquipTdmTrailsEntry 10 }

genEquipTdmTrailDest1Type		OBJECT-TYPE
		SYNTAX 		TrailIfType
		ACCESS		read-write
        STATUS		mandatory
        DESCRIPTION
		"The interface type destination of the trail."
::= { genEquipTdmTrailsEntry 11 }

genEquipTdmTrailDest1Num		OBJECT-TYPE
		SYNTAX 		INTEGER
		ACCESS		read-write
        STATUS		mandatory
        DESCRIPTION
		"The destination interface number."
::= { genEquipTdmTrailsEntry 12 }

genEquipTdmTrailDest2Slot		OBJECT-TYPE
		SYNTAX 		INTEGER
		ACCESS		read-write
        STATUS		mandatory
        DESCRIPTION
		"A secondary slot number that is being used when protection is enabled. "
::= { genEquipTdmTrailsEntry 13 }

genEquipTdmTrailDest2Type		OBJECT-TYPE
		SYNTAX 		TrailIfType
		ACCESS		read-write
        STATUS		mandatory
        DESCRIPTION
		"A secondary interface type that is being used when protection is enabled."
::= { genEquipTdmTrailsEntry 14 }

genEquipTdmTrailDest2Num		OBJECT-TYPE
		SYNTAX 		INTEGER
		ACCESS		read-write
        STATUS		mandatory
        DESCRIPTION
		"A secondary interface number that is being used when protection is enabled."
::= { genEquipTdmTrailsEntry 15 }

genEquipTdmTrailProtectedForceActive		OBJECT-TYPE
		SYNTAX 		TrailProtectedType
		ACCESS		read-write
        STATUS		mandatory
        DESCRIPTION
		"Force active of the primary or the secondary trails."
::= { genEquipTdmTrailsEntry 16 }

genEquipTdmTrailProtectedActiveTrail		OBJECT-TYPE
		SYNTAX 		TrailProtectedType
		ACCESS		read-only
        STATUS		mandatory
        DESCRIPTION
		"The trail current active path. That tells us Who is the active trail."
::= { genEquipTdmTrailsEntry 17 }

genEquipTdmTrailProtectedNumOfSwitches		OBJECT-TYPE
		SYNTAX 		INTEGER
		ACCESS		read-only
        STATUS		mandatory
        DESCRIPTION
		"The value represent the number of switches in SNCP between the primary and secondary trails.
		Setting this value to 0, clears this counter"
::= { genEquipTdmTrailsEntry 18 }

genEquipTdmTrailPrimaryPathAlarmStatus		OBJECT-TYPE
		SYNTAX 		INTEGER
		ACCESS		read-only
        STATUS		mandatory
        DESCRIPTION
		"The alarm status of the trail primary path.
		The value is a Bit Map: Id-Mismatch(0x01), 
		Excessive-Ber(0x02), Signal-Degrade-Ber(0x04), 
		Invalid-Trail-Status(0x08), Signal-Failure(0x10), RDI-Detected(0x20)."
::= { genEquipTdmTrailsEntry 19 }

genEquipTdmTrailSecondaryPathAlarmStatus		OBJECT-TYPE
		SYNTAX 		INTEGER
		ACCESS		read-only
        STATUS		mandatory
        DESCRIPTION
		"The alarm status of the trail secondary path.
		The value is a Bit Map: Id-Mismatch(0x01), 
		Excessive-Ber(0x02), Signal-Degrade-Ber(0x04), 
		Invalid-Trail-Status(0x08), Signal-Failure(0x10), RDI-Detected(0x20)."
::= { genEquipTdmTrailsEntry 20 }

genEquipTdmTrailRowStatus		OBJECT-TYPE
		SYNTAX 		RowStatus
		ACCESS		read-write
        STATUS		mandatory
        DESCRIPTION
		"The Row status of the entry."
::= { genEquipTdmTrailsEntry 30 }

-- Protected trail force active all trails command
genEquipTdmTrailsProtectedForceActiveAllCmd		OBJECT-TYPE
		SYNTAX 		TrailProtectedType
		ACCESS		read-write
        STATUS		mandatory
        DESCRIPTION
		"Force all active trails to be either primary or secondary."
::= { genEquipTdmTrails 2 }

-- Protected trail force operational or reserved all trails command
genEquipTdmTrailsProtectedForceOperationalOrReservedCmd		OBJECT-TYPE
		SYNTAX 		INTEGER {
						reserved(0),
						operational(1),
						idle(30)
		}
		ACCESS		read-write
        STATUS		mandatory
        DESCRIPTION
		"Force all active trails to be either operational or reserved."
::= { genEquipTdmTrails 3 }

genEquipTdmTrailsProtectedRevertiveSwitchTimeout  OBJECT-TYPE
        SYNTAX INTEGER   (0..1800)
		ACCESS		read-write
        STATUS		mandatory
        DESCRIPTION
		"The revertive switch timeout in seconds for revertive protected trails."
::= { genEquipTdmTrails 4 }

genEquipTdmTrailsSwitchCounterClear  OBJECT-TYPE
        SYNTAX 		OffOn
		ACCESS		read-write
        STATUS		mandatory
        DESCRIPTION
		"This parameter will clear the counter for protected switches."
::= { genEquipTdmTrails 5 }

genEquipTdmTrailsDeleteAllTrails  OBJECT-TYPE
		SYNTAX          OffOn
		ACCESS          read-write
		STATUS          mandatory
        DESCRIPTION
        "This parameter will delete all existing trails."
::= { genEquipTdmTrails 6 }

-- Synchronization
genEquipSynchronization	OBJECT IDENTIFIER ::= {genEquipServices 3}

genEquipSynchronizationSrcTable  OBJECT-TYPE
        SYNTAX  SEQUENCE OF GenEquipSynchronizationSrcEntry
        ACCESS  not-accessible
        STATUS mandatory
        DESCRIPTION
        "Synchronization source table."
        ::= { genEquipSynchronization 1 }

genEquipSynchronizationSrcEntry OBJECT-TYPE
        SYNTAX GenEquipSynchronizationSrcEntry
        ACCESS not-accessible
        STATUS mandatory
          DESCRIPTION
          "Synchronization source table."
        INDEX { genEquipSynchronizationSrcPriority }
        ::= { genEquipSynchronizationSrcTable 1 }

GenEquipSynchronizationSrcEntry ::=
		SEQUENCE {
			genEquipSynchronizationSrcPriority 
            	INTEGER,
			genEquipSynchronizationSrcSlot 
            	INTEGER,
			genEquipSynchronizationSrcType 
            	INTEGER,
			genEquipSynchronizationSrcNum 
            	INTEGER,
			genEquipSynchronizationSrcValid 
            	INTEGER,
			genEquipSynchronizationSrcTrail 
            	EnableDisable,
			genEquipSynchronizationSrcAdmin 
            	EnableDisable,
			genEquipSynchronizationSrcQuality 
            	INTEGER,
			genEquipSynchronizationSrcReceivedSSM 
            	INTEGER,
			genEquipSynchronizationSrcQualityStatus 
            	INTEGER
            	
}

genEquipSynchronizationSrcPriority		OBJECT-TYPE
		SYNTAX 		INTEGER (1..8)
		ACCESS		read-only
        STATUS		mandatory
        DESCRIPTION
		"The source for system synchronization (primary, seconday)."
::= { genEquipSynchronizationSrcEntry 1 }

genEquipSynchronizationSrcSlot		OBJECT-TYPE
		SYNTAX 		SlotId
		ACCESS		read-write
        STATUS		mandatory
        DESCRIPTION
		"The slot number of the sync source (1..6).
		Possible values:
		 - standalone(0)
		 - slot1(1)
		 - slot2(2)
		 - slot3(3)
		 - slot4(4)
		 - slot5(5)
		- slot6(6)"
::= { genEquipSynchronizationSrcEntry 2 }

genEquipSynchronizationSrcType		OBJECT-TYPE
		SYNTAX 		INTEGER {
			unknown(-1),
			line(0),
			radio-ch(1),
			stm-vc(2),
			stm-signal(4),
			ether(5)
		}
		ACCESS		read-write
        STATUS		mandatory
        DESCRIPTION
		"The interface type (line (PDH), Radio, STM-1/OC-3)."
::= { genEquipSynchronizationSrcEntry 3 }

genEquipSynchronizationSrcNum		OBJECT-TYPE
		SYNTAX 		INTEGER
		ACCESS		read-write
        STATUS		mandatory
        DESCRIPTION
		"The sync source number: VC in STM-1/OC-3, Radio channel in case the interface is Radio, or E1 number in
		case the interface is PDH (E1s)."
::= { genEquipSynchronizationSrcEntry 4 }

genEquipSynchronizationSrcValid		OBJECT-TYPE
		SYNTAX 		INTEGER {
						not-valid(0), 
						valid(1)
		}
		ACCESS		read-only
        STATUS		mandatory
        DESCRIPTION
		"This paremter is the source status, if the source if valid or not.
		In case it is valid, it means that the clock being extracted from the source is ok and can be used.
		In case it is not-valid the source is not in use, each interface will have it's own clock."
::= { genEquipSynchronizationSrcEntry 5 }

genEquipSynchronizationSrcTrail		OBJECT-TYPE
		SYNTAX 		EnableDisable
		ACCESS		read-write
        STATUS		mandatory
        DESCRIPTION
		"This parameter indicates whether the synchronization source is the 
		signal of an existing co-located TDM trail used for traffic. 
		Enabling this parameter in an interface which does not belong to a trail will fail, 
		as well as disabling it for an interface which belongs to a trail."
::= { genEquipSynchronizationSrcEntry 6 }

genEquipSynchronizationSrcAdmin		OBJECT-TYPE
		SYNTAX 		EnableDisable
		ACCESS		read-write
        STATUS		mandatory
        DESCRIPTION
		"Admin state of the sync source (the sync source is enabled or disabled)."
::= { genEquipSynchronizationSrcEntry 7 }

genEquipSynchronizationSrcQuality		OBJECT-TYPE
		SYNTAX 		INTEGER {
						automatic  (0),
						g811      (2),
						ssu-a      (4),
						ssu-b      (8),
						g813-8262  (11),
						do-not-use (15)
		}
		ACCESS		read-write
        STATUS		mandatory
        DESCRIPTION
		"..."
::= { genEquipSynchronizationSrcEntry 8 }

genEquipSynchronizationSrcReceivedSSM		OBJECT-TYPE
		SYNTAX 		INTEGER
		ACCESS		read-only
        STATUS		mandatory
        DESCRIPTION
		"..."
::= { genEquipSynchronizationSrcEntry 9 }

genEquipSynchronizationSrcQualityStatus		OBJECT-TYPE
		SYNTAX 		INTEGER
		ACCESS		read-only
        STATUS		mandatory
        DESCRIPTION
		"..."
::= { genEquipSynchronizationSrcEntry 10 }



-- The following tables are accessed by its slot, there is no indirect access to this tables through main slot
-- Radio Clock Source
genEquipSynchronizationRadioClkSrcSource		OBJECT-TYPE
		SYNTAX 		INTEGER 
		ACCESS		read-write
        STATUS		mandatory
        DESCRIPTION
		"This parameters determines whether the system reference frequency is transported through the radio.
         0 indicates that the outgoing signal takes its clock from an independant local clock.
         channel number indicates that the clock is from that radio-channel reference clock, 
         as taken from the synchronization source interface."
::= { genEquipSynchronization 3 }

genEquipSynchronizationSDHClkSrcSource		OBJECT-TYPE
		SYNTAX 		INTEGER 
		ACCESS		read-write
        STATUS		mandatory
        DESCRIPTION
		"This parameters determines whether the system reference frequency is transported 
         through the interface. if value is 0 it indicates that the outgoing signal takes its 
		 clock from an independant local clock.
         system-clock-source indicates that the clock is from the system reference clock, 
         as taken from the synchronization source interface."
::= { genEquipSynchronization 4 }

genEquipSynchronizationPDHClkSrcTable  OBJECT-TYPE
        SYNTAX  SEQUENCE OF GenEquipSynchronizationPDHClkSrcEntry
        ACCESS  not-accessible
        STATUS mandatory
        DESCRIPTION
        "Synchronization source table."
        ::= { genEquipSynchronization 5 }

genEquipSynchronizationPDHClkSrcEntry OBJECT-TYPE
        SYNTAX GenEquipSynchronizationPDHClkSrcEntry
        ACCESS not-accessible
        STATUS mandatory
          DESCRIPTION
          "Synchronization source table."
        INDEX { genEquipSynchronizationPDHClkSrcIFNum }
        ::= { genEquipSynchronizationPDHClkSrcTable 1 }

GenEquipSynchronizationPDHClkSrcEntry ::=
		SEQUENCE {
			genEquipSynchronizationPDHClkSrcIFNum
				INTEGER,
			genEquipSynchronizationPDHClkSrcSource 
            	INTEGER
}

genEquipSynchronizationPDHClkSrcIFNum		OBJECT-TYPE
		SYNTAX 		INTEGER 
		ACCESS		read-write
        STATUS		mandatory
        DESCRIPTION
		"This parameters the interface which is configured to take the system reference clock 
        or a local clock in genEquipSynchronizationSDHClkSrcSource.
        The number indicates the E1/DS1 interface being configured (1-32)."
::= { genEquipSynchronizationPDHClkSrcEntry 2 }

genEquipSynchronizationPDHClkSrcSource		OBJECT-TYPE
		SYNTAX 		INTEGER {
				local-clock(0), 
				system-clock-source(1)
		}
		ACCESS		read-write
        STATUS		mandatory
        DESCRIPTION
		"This parameters determines whether the system reference frequency is transported 
         through the interface defined in genEquipSynchronizationPDHClkSrcIFNum.
         local-clock indicates that the outgoing signal takes its clock from an independant local clock.
         system-clock-source indicates that the clock is from the system reference clock,
         as taken from the synchronization source interface."
::= { genEquipSynchronizationPDHClkSrcEntry 3 }

genEquipSynchronizationPRCRegeneratorMode		OBJECT-TYPE
		SYNTAX EnableDisable
		ACCESS		read-write
        STATUS		mandatory
        DESCRIPTION
		"This parameter sets the IDU to point-to-point PRC quality frequency distribution mode. 
		Notice that this is relevant only for smart pipe applications"
::= { genEquipSynchronization 6 }

genEquipSynchronizationPRCRegeneratorDirection OBJECT-TYPE
		SYNTAX INTEGER {
			line-to-radio (0),
			radio-to-line (1)
		}
		ACCESS		read-write
        STATUS		mandatory
        DESCRIPTION
		"This parameter sets the direction in which the frequency signal is transported, 
		in the case of electrical GBE interfaces. 
		Notice that for optical interfaces, this parameter has no effect."
::= { genEquipSynchronization 7 }


genEquipSynchronizationSrcRevertiveTimer		OBJECT-TYPE
		SYNTAX INTEGER (0..30)
		ACCESS		read-write
        STATUS		mandatory
        DESCRIPTION
		"this parameter sets the timeout (in seconds) for a counter which is set once
    	an interface recovers from a failure; after this timeout the interface will be considered
    	stable and can be used as a synchronization source. A value of zero means no timer."
::= { genEquipSynchronization 8 }

genEquipSynchronizationSrcActiveSyncSourceIndex		OBJECT-TYPE
		SYNTAX INTEGER
		ACCESS		read-only
        STATUS		mandatory
        DESCRIPTION
		"The active synchronization source."
::= { genEquipSynchronization 9 }

genEquipSynchronizationNodeMode		OBJECT-TYPE
		SYNTAX INTEGER {
				automatic (0),
				force (1)
		}
		ACCESS		read-write
        STATUS		mandatory
        DESCRIPTION
		"..."
::= { genEquipSynchronization 10 }

genEquipSynchronizationForceSource		OBJECT-TYPE
		SYNTAX INTEGER (0..8)
		ACCESS		read-write
        STATUS		mandatory
        DESCRIPTION
		"The active synchronization source, 0 is internal."
::= { genEquipSynchronization 11 }

genEquipSynchronizationSystemReferenceQuality		OBJECT-TYPE
		SYNTAX INTEGER
		ACCESS		read-only
        STATUS		mandatory
        DESCRIPTION
		"..."
::= { genEquipSynchronization 12 }

genEquipSynchronizationRegeneratorSSMAdmin		OBJECT-TYPE
		SYNTAX INTEGER
		ACCESS		read-write
        STATUS		mandatory
        DESCRIPTION
		"..."
::= { genEquipSynchronization 13 }



-- Interfaces
genEquipInterfaces	OBJECT IDENTIFIER ::= {genEquip 9}

-- Interfaces - Ethernet
genEquipInterfacesEther	OBJECT IDENTIFIER ::= {genEquipInterfaces 1}

genEquipInterfacesEtherTable  OBJECT-TYPE
        SYNTAX  SEQUENCE OF GenEquipInterfacesEtherEntry
        ACCESS  not-accessible
        STATUS mandatory
        DESCRIPTION
        "Ethernet interface configuration and status table. 
        The index of the table is via ifIndex, as well as the operational status and the admin state, 
        speed and port connector."
        ::= { genEquipInterfacesEther 1 }

genEquipInterfacesEtherEntry OBJECT-TYPE
        SYNTAX GenEquipInterfacesEtherEntry
        ACCESS not-accessible
        STATUS mandatory
        DESCRIPTION
        "Ethernet interface configuration and status table. 
        The index of the table is via ifIndex, as well as the operational status and the admin state, 
        speed and port connector."
        INDEX { ifIndex }
        ::= { genEquipInterfacesEtherTable 1 }

GenEquipInterfacesEtherEntry ::=
		SEQUENCE {
			genEquipInterfacesEtherConnType	
				INTEGER,
			genEquipInterfacesEtherPortType
				INTEGER,
			genEquipInterfacesEtherAutoNegotiation
				INTEGER,
			genEquipInterfacesEtherDuplex
				HalfFull,
			genEquipInterfacesEtherRate
				RateMbps,
			genEquipInterfacesEtherPortLerningAdmin
				EnableDisable,
			genEquipInterfacesEtherFlowCtrl
				INTEGER,
			genEquipInterfacesEtherLagPortMember
				INTEGER,
			genEquipInterfacesEtherActualDuplex
				HalfFull,
			genEquipInterfacesEtherActualRate
				RateMbps,
			genEquipInterfacesEtherClkSrc
				INTEGER,
			genEquipInterfacesEtherPortServiceType
				INTEGER
}

genEquipInterfacesEtherConnType OBJECT-TYPE
        SYNTAX INTEGER  {
			not-applicable(-1),
            rj45(0),
		    electricalSFP(1),
		    opticalSFP(2),
		    radio(3),
			na(4)
        }
        ACCESS read-write
        STATUS mandatory
        DESCRIPTION
        "The physical interface type. For port 8 the only valid value is radio. For ports 3 to 7 the only valid
	     value is rj45."
        ::= { genEquipInterfacesEtherEntry 1 }


genEquipInterfacesEtherPortType OBJECT-TYPE
        SYNTAX INTEGER { 
			not-applicable(-1),
			access(0),
			trunk(1),
			hybrid(2),
			cN(3),
			pN(4),
			management(30),
			wayside(31)
		} 
        ACCESS read-write
        STATUS mandatory
        DESCRIPTION
        "The type of the port. 
        Access - untagged port (in case of managed switch).
        Trunk - C-VID tagged port (in case of managed switch).
        CN - Don't care on the vlan tag (in case of metro switch configuration).
        SN - S-VID is used as the first vlan (in case of metro switch configuration)."
        ::= { genEquipInterfacesEtherEntry 2 }
		
genEquipInterfacesEtherAutoNegotiation OBJECT-TYPE
        SYNTAX INTEGER { 
		  not-applicable(-1),
          off(0), 
          on(1) 
        }
        ACCESS read-write
        STATUS mandatory
        DESCRIPTION
        "Enable or disable auto-negotiation on the port."
        ::= { genEquipInterfacesEtherEntry 3 }

genEquipInterfacesEtherDuplex OBJECT-TYPE
        SYNTAX HalfFull
        ACCESS read-write
        STATUS mandatory
        DESCRIPTION
        "Half or full duplex."
        ::= { genEquipInterfacesEtherEntry 4 }  
        
genEquipInterfacesEtherRate OBJECT-TYPE
        SYNTAX RateMbps
        ACCESS read-write
        STATUS mandatory
        DESCRIPTION
        "10, 100 OR 1000 Mbps."
        ::= { genEquipInterfacesEtherEntry 5 }

genEquipInterfacesEtherPortLerningAdmin OBJECT-TYPE
       SYNTAX INTEGER { 
          not-applicable(-1),
          enable(2), 
          disable(3) 
        }
        ACCESS read-write
        STATUS mandatory
        DESCRIPTION
        "Enable or disable MAC address learning in the port."
        ::= { genEquipInterfacesEtherEntry 6 }

genEquipInterfacesEtherFlowCtrl OBJECT-TYPE
        SYNTAX INTEGER {
					not-applicable(-1),
					off(0),
					on(1),
					na(2)
		}
        ACCESS read-write
        STATUS mandatory
        DESCRIPTION
        "Enable or disable flow control on the port. Supported only in pipe mode. "
        ::= { genEquipInterfacesEtherEntry 7 }

genEquipInterfacesEtherLagPortMember OBJECT-TYPE
       SYNTAX INTEGER { 
		  not-applicable(-1),
          not-aggrigated(0), 
          group-1(1),
          group-2(2),
          group-3(3)
        }
        ACCESS read-write
        STATUS mandatory
        DESCRIPTION
        "The syntax is ifIndex, or FFFF for port that is not member in a lag."
        ::= { genEquipInterfacesEtherEntry 8 }

genEquipInterfacesEtherActualDuplex OBJECT-TYPE
        SYNTAX HalfFull
        ACCESS read-only
        STATUS mandatory
        DESCRIPTION
        "Actual duplex (in auto-negotiation, the mode the two ports agreed upon) - Half or full duplex."
        ::= { genEquipInterfacesEtherEntry 9 }  
        
genEquipInterfacesEtherActualRate OBJECT-TYPE
        SYNTAX RateMbps
        ACCESS read-only
        STATUS mandatory
        DESCRIPTION
         "Actual rate (in auto-negotiation, the rate the two ports agreed upon) - 10, 100 OR 1000 Mbps."
        ::= { genEquipInterfacesEtherEntry 10 }  
        
genEquipInterfacesEtherClkSrc OBJECT-TYPE
       SYNTAX INTEGER { 
		  not-applicable(-1),
          local-clock(0), 
          system-clock-source(1) 
        }
        ACCESS read-write
        STATUS mandatory
        DESCRIPTION
        "The source for the outgoing carrier signal clock. Local-clock is an internal independent oscilator.
	   system-clock-source causes the ethernet clock to be derived from the defined system clock source 
	   (which can be taken from another interface)
	   Note: changing this parameter per port affect all the Ethernet ports." 
        ::= { genEquipInterfacesEtherEntry 11 }

genEquipInterfacesEtherPortServiceType OBJECT-TYPE
        SYNTAX INTEGER { 
		  		not-applicable(-1),
				sap(0), 
				snp(1) 
		}
        ACCESS read-write
        STATUS mandatory
        DESCRIPTION
        ".This parameter indicates whether the port is being used as a Service Access Point (SAP) 
		or as a Service Network Point (SNP) in a network-wide Ethernet service; 
		the parameter has no functionality, but is meant to hold data for the NMS." 
        ::= { genEquipInterfacesEtherEntry 12 }
                             		
genEquipInterfacesEtherStatePropagation  OBJECT-TYPE
        SYNTAX  INTEGER  {
                none(0) ,
		        lof-loc(1) ,
		        lof-loc-excber(3) ,
		        lof-loc-remote(5) ,
		        lof-loc-excber-remote(7) ,
		        lof(9) ,
		        lof-excber(11) ,
		        lof-remote(13) ,
		        lof-excber-remote(15)
        }
      	ACCESS  read-write
        STATUS mandatory
        DESCRIPTION
        "This parameter configures the behavior of Ethernet ports in single 
        pipe mode. When a failure is detected, ports will be automatically shut 
        down when the configured conditions take place. The possible choices 
        are a combination of the following failures in the local and the remote IDUs: 
        radio LOF, Ethernet line LOC, radio excessive ber"        
		::= { genEquipInterfacesEther 2 }

-- Interfaces E1/T1
genEquipInterfacesE1T1	OBJECT IDENTIFIER ::= {genEquipInterfaces 2}

genEquipInterfacesE1T1PortGroupTable  OBJECT-TYPE
        SYNTAX  SEQUENCE OF GenEquipInterfacesE1T1PortGroupEntry
        ACCESS  not-accessible
        STATUS mandatory
        DESCRIPTION
        "General parameters for group of E1 or T1 interfaces."
        ::= { genEquipInterfacesE1T1 1 }

genEquipInterfacesE1T1PortGroupEntry OBJECT-TYPE
        SYNTAX GenEquipInterfacesE1T1PortGroupEntry
        ACCESS not-accessible
        STATUS mandatory
          DESCRIPTION
          "General parameters for group of E1 or T1 interfaces."
        INDEX { genEquipInterfacesE1T1PortGroupId }
        ::= { genEquipInterfacesE1T1PortGroupTable 1 }

GenEquipInterfacesE1T1PortGroupEntry ::=
		SEQUENCE {
			genEquipInterfacesE1T1PortGroupId
            	INTEGER,
			genEquipInterfacesE1T1PortGroupLineCode
            	INTEGER,
			genEquipInterfacesE1T1PortGroupExcessiveBERthreshold
            	BerLevel,
			genEquipInterfacesE1T1PortGroupSignalDegradeThreshold
            	INTEGER,
			genEquipInterfacesE1T1PortGroupLineCode1to8
            	INTEGER,
			genEquipInterfacesE1T1PortGroupLineCode9to16
            	INTEGER,
			genEquipInterfacesE1T1PortGroupLineCode17to24
            	INTEGER,
			genEquipInterfacesE1T1PortGroupLineCode25to32
            	INTEGER
}

genEquipInterfacesE1T1PortGroupId OBJECT-TYPE
        SYNTAX INTEGER
        ACCESS read-only
        STATUS mandatory
        DESCRIPTION
        "Group id. the index of this table."
        ::= { genEquipInterfacesE1T1PortGroupEntry 1 }

genEquipInterfacesE1T1PortGroupLineCode OBJECT-TYPE
        SYNTAX INTEGER {
					b8zs(1),
					ami(2),
					hdb3(3)
		}
        ACCESS read-write
        STATUS mandatory
        DESCRIPTION
        "The PDH line coding. b8zs is for T1 and hdb3 for E1.
        ami is only for T1. This parameter is 
        relevant only for versions up to 6.6.0.0.1.53 (including)."
        ::= { genEquipInterfacesE1T1PortGroupEntry 2 }

genEquipInterfacesE1T1PortGroupExcessiveBERthreshold OBJECT-TYPE
        SYNTAX BerLevel
        ACCESS read-write
        STATUS mandatory
        DESCRIPTION
        "Excessive BER threshold for the group of E1s/T1s."
        ::= { genEquipInterfacesE1T1PortGroupEntry 3 }

genEquipInterfacesE1T1PortGroupSignalDegradeThreshold OBJECT-TYPE
        SYNTAX INTEGER { n1e-6(3), n1e-7(4), n1e-8(5), n1e-9(6)  }
        ACCESS read-write
        STATUS mandatory
        DESCRIPTION
        "Signal degrade threshold for the group of E1s/T1s."
        ::= { genEquipInterfacesE1T1PortGroupEntry 4 }
        
genEquipInterfacesE1T1PortGroupLineCode1to8 OBJECT-TYPE
        SYNTAX INTEGER {
					b8zs(1),
					ami(2),
					hdb3(3)
		}
        ACCESS read-write
        STATUS mandatory
        DESCRIPTION
        "The PDH line coding for line interfaces 1 to 8. 
        b8zs is for T1 and hdb3 for E1. ami is only for T1."
        ::= { genEquipInterfacesE1T1PortGroupEntry 5 }
        
genEquipInterfacesE1T1PortGroupLineCode9to16 OBJECT-TYPE
        SYNTAX INTEGER {
					b8zs(1),
					ami(2),
					hdb3(3)
		}
        ACCESS read-write
        STATUS mandatory
        DESCRIPTION
        "The PDH line coding for line interfaces 9 to 16. 
        b8zs is for T1 and hdb3 for E1. ami is only for T1."
        ::= { genEquipInterfacesE1T1PortGroupEntry 6 }
        
genEquipInterfacesE1T1PortGroupLineCode17to24 OBJECT-TYPE
        SYNTAX INTEGER {
					b8zs(1),
					ami(2),
					hdb3(3)
		}
        ACCESS read-write
        STATUS mandatory
        DESCRIPTION
        "The PDH line coding for line interfaces 17 to 24.
        b8zs is for T1 and hdb3 for E1. ami is only for T1."
        ::= { genEquipInterfacesE1T1PortGroupEntry 7 }
        
genEquipInterfacesE1T1PortGroupLineCode25to32 OBJECT-TYPE
        SYNTAX INTEGER {
					b8zs(1),
					ami(2),
					hdb3(3)
		}
        ACCESS read-write
        STATUS mandatory
        DESCRIPTION
        "The PDH line coding for interfaces 25 to 32. 
        b8zs is for T1 and hdb3 for E1. ami is only for T1."
        ::= { genEquipInterfacesE1T1PortGroupEntry 8 }                                



genEquipInterfacesE1T1Table  OBJECT-TYPE
        SYNTAX  SEQUENCE OF GenEquipInterfacesE1T1Entry
        ACCESS  not-accessible
        STATUS mandatory
        DESCRIPTION
        "E1/T1 interface configuration table."
        ::= { genEquipInterfacesE1T1 2 }

genEquipInterfacesE1T1Entry OBJECT-TYPE
        SYNTAX GenEquipInterfacesE1T1Entry
        ACCESS not-accessible
        STATUS mandatory
          DESCRIPTION
          "E1/T1 interface configuration table."
        INDEX { ifIndex }
        ::= { genEquipInterfacesE1T1Table 1 }

GenEquipInterfacesE1T1Entry ::=
		SEQUENCE {
			genEquipInterfacesE1T1Priority
            	INTEGER,
			genEquipInterfacesE1T1CurrBER
            	BerLevel,
			genEquipInterfacesE1T1Loopback
            	INTEGER,
            genEquipInterfacesE1T1AISSStatus
            	INTEGER,
            genEquipInterfacesE1T1CableLength
            	INTEGER
}

genEquipInterfacesE1T1Priority OBJECT-TYPE
        SYNTAX INTEGER { low(1), high(2) }
        ACCESS read-only
        STATUS mandatory
        DESCRIPTION
        "The ACM priority of the E1/T1.
	   This parameter is relevant only for stand-alone mode.
	   In shelf this parameter is defined in the trail configuration."
        ::= { genEquipInterfacesE1T1Entry 1 }
		
genEquipInterfacesE1T1CurrBER OBJECT-TYPE
        SYNTAX BerLevel 
        ACCESS read-only
        STATUS mandatory
        DESCRIPTION
        "E1/T1 current BER."
        ::= { genEquipInterfacesE1T1Entry 2 }
		
genEquipInterfacesE1T1Loopback OBJECT-TYPE
        SYNTAX INTEGER {
						off(1),
						towardsLine(2),
						towardsRadio(3)
						} 
        ACCESS read-write
        STATUS mandatory
        DESCRIPTION
        "Enable or Disable line loopback on the E1/T1 interface."
        ::= { genEquipInterfacesE1T1Entry 3 }

genEquipInterfacesE1T1AISSStatus OBJECT-TYPE
        SYNTAX INTEGER {
                         detected(0),
                         notDetected(1)
        } 
        ACCESS read-only
        STATUS mandatory
        DESCRIPTION
        "Status of the AIS detection, if the AIS detection is activated."
        ::= { genEquipInterfacesE1T1Entry 4 }
                            
genEquipInterfacesE1T1CableLength OBJECT-TYPE
        SYNTAX INTEGER {
                         len-0-133ft-0-41m(1),
                         len-133ft-266ft-41m-81m(2),
                         len-266ft-399ft-81m-122m(3),
                         len-399ft-533ft-122m-162m(4),
                         len-533ft-655ft-162m-200m(5)
        } 
        ACCESS read-write
        STATUS mandatory
        DESCRIPTION
        "This parameter is valid only for T1 interfaces, and determines cable length range."
        ::= { genEquipInterfacesE1T1Entry 5 }
		                 
		                 
		                 
genEquipInterfacesAux	OBJECT IDENTIFIER ::= {genEquipInterfaces 3}

-- Interfaces Way Side
genEquipInterfacesAuxWaySide	OBJECT IDENTIFIER ::= {genEquipInterfacesAux 1}

genEquipInterfacesAuxWaySideTable  OBJECT-TYPE
        SYNTAX  SEQUENCE OF GenEquipInterfacesAuxWaySideEntry
        ACCESS  not-accessible
        STATUS mandatory
        DESCRIPTION
        "Way-side interface configuration."
        ::= { genEquipInterfacesAuxWaySide 1 }

genEquipInterfacesAuxWaySideEntry OBJECT-TYPE
        SYNTAX GenEquipInterfacesAuxWaySideEntry
        ACCESS not-accessible
        STATUS mandatory
          DESCRIPTION
          "Way-side interface configuration."
        INDEX { ifIndex }
        ::= { genEquipInterfacesAuxWaySideTable 1 }

GenEquipInterfacesAuxWaySideEntry ::=
		SEQUENCE {
			genEquipInterfacesAuxWaySideAdmin 
            	EnableDisable,
			genEquipInterfacesAuxWaySideCapacity
				INTEGER,
			genEquipInterfacesAuxWaySideAutoNegotiation
				OffOn,
			genEquipInterfacesAuxWaySideDuplex
				INTEGER,
			genEquipInterfacesAuxWaySideRate
				RateMbps
}                       

genEquipInterfacesAuxWaySideAdmin OBJECT-TYPE
        SYNTAX EnableDisable
        ACCESS read-write
        STATUS mandatory
        DESCRIPTION
        "Enable - Set Ethernet port #4 to be a wayside port. Disabling this option will cause the port to behave
	   as a normal traffic Ethernet port."
        ::= { genEquipInterfacesAuxWaySideEntry 1 }


genEquipInterfacesAuxWaySideCapacity OBJECT-TYPE
        SYNTAX INTEGER { narrow(0), wide(1) }
        ACCESS read-write
        STATUS mandatory
        DESCRIPTION
        "Narrow band (64Kbps) or Wide band (2Mbps)"
        ::= { genEquipInterfacesAuxWaySideEntry 2 }   
        
        
genEquipInterfacesAuxWaySideAutoNegotiation OBJECT-TYPE
        SYNTAX OffOn
        ACCESS read-write
        STATUS mandatory
        DESCRIPTION
        "Wayside port auto negotiation (Off, on)"
        ::= { genEquipInterfacesAuxWaySideEntry 3 }
        
genEquipInterfacesAuxWaySideDuplex OBJECT-TYPE
        SYNTAX INTEGER {
        		not-applicable(-1), 
        		half(0), 
        		full(1)
        }
        ACCESS read-write
        STATUS mandatory
        DESCRIPTION
        "Wayside port duplex (Half, Full)"
        ::= { genEquipInterfacesAuxWaySideEntry 4 }
        
genEquipInterfacesAuxWaySideRate OBJECT-TYPE
        SYNTAX INTEGER {
        		not-applicable(-1), 
        		n10(0), 
        		n100(1)
        }
        ACCESS read-write
        STATUS mandatory
        DESCRIPTION
        "Wayside interface port rate (10Mbps,100Mbps)"
        ::= { genEquipInterfacesAuxWaySideEntry 5 }
        
		

		
-- Interfaces User channel
genEquipInterfacesAuxUserChanTable  OBJECT-TYPE
        SYNTAX  SEQUENCE OF GenEquipInterfacesAuxUserChanEntry
        ACCESS  not-accessible
        STATUS mandatory
        DESCRIPTION
        "Table of configured user channels."
        ::= { genEquipInterfacesAux 2 }

genEquipInterfacesAuxUserChanEntry OBJECT-TYPE
        SYNTAX GenEquipInterfacesAuxUserChanEntry
        ACCESS not-accessible
        STATUS mandatory
          DESCRIPTION
          "Table of configured user channels."
        INDEX { ifIndex }
        ::= { genEquipInterfacesAuxUserChanTable 1 }

GenEquipInterfacesAuxUserChanEntry ::=
		SEQUENCE {
			genEquipInterfacesAuxUserChanType
				INTEGER
}

genEquipInterfacesAuxUserChanType OBJECT-TYPE
        SYNTAX INTEGER { 
				asynchronous-rs232(1), 
				asynchronous-v-11(2),
				twin-asynchronous-rs232-and-v-11(3),
				synchronous-v-11-codirectional(4),
				synchronous-v-11-contradirectional(5)
		}
        ACCESS read-write
        STATUS mandatory
        DESCRIPTION
        "User channel type. The asynchronous modes allow two channels, one in each port. 
		The twin asynchronous mode uses port 1 for v.11 and port 2 for RS-232. 
		The Synchronous modes use two ports each"
        ::= { genEquipInterfacesAuxUserChanEntry 1 }

		
-- Interfaces Sonet/SDH
genEquipInterfacesSdh	OBJECT IDENTIFIER ::= {genEquipInterfaces 4}

genEquipInterfacesSdhTable  OBJECT-TYPE
        SYNTAX  SEQUENCE OF GenEquipInterfacesSdhEntry
        ACCESS  not-accessible
        STATUS mandatory
        DESCRIPTION
        "STM-1,OC-3 interface configuration and status table. "
        ::= { genEquipInterfacesSdh 1 }

genEquipInterfacesSdhEntry OBJECT-TYPE
        SYNTAX GenEquipInterfacesSdhEntry
        ACCESS not-accessible
        STATUS mandatory
          DESCRIPTION
          "STM-1,OC-3 interface configuration and status table."
        INDEX { ifIndex }
        ::= { genEquipInterfacesSdhTable 1 }

GenEquipInterfacesSdhEntry ::=
		SEQUENCE {
			genEquipInterfacesSdhMuteTx
            	EnableDisableSMI2,
			genEquipInterfacesSdhClockSource
            	INTEGER,
			genEquipInterfacesSdhAISAdmin
            	EnableDisable,
			genEquipInterfacesSdhTraceIdReceived
            	DisplayString,
			genEquipInterfacesSdhTraceIdTransmitted
            	DisplayString,
			genEquipInterfacesSdhTraceIdExpected
            	DisplayString,
			genEquipInterfacesSdhTraceIdStringLength
            	INTEGER,
			genEquipInterfacesSdhExcessiveBer
            	INTEGER,
			genEquipInterfacesSdhSignalDegrade
            	INTEGER,
			genEquipInterfacesSdhLoopback
				INTEGER,
			genEquipInterfacesSdhClockSourceStatus
				INTEGER,
			genEquipInterfacesSdhLineTxProtectionMode
				INTEGER,
			genEquipInterfacesSdhSyncVC
				INTEGER
}

genEquipInterfacesSdhMuteTx OBJECT-TYPE
        SYNTAX EnableDisableSMI2
        ACCESS read-write
        STATUS mandatory
        DESCRIPTION
        "Mute Tx option on the interface."
        ::= { genEquipInterfacesSdhEntry 1 }
				
genEquipInterfacesSdhClockSource OBJECT-TYPE
        SYNTAX INTEGER {
					internal-clock(0),
					loop(1),
					synchronization-vc(2)
		}
        ACCESS read-write
        STATUS mandatory
        DESCRIPTION
        "The source of the clock being used.
        sync-vc option is for future support, to use one of the outgoing TDM VCs as a source."
        ::= { genEquipInterfacesSdhEntry 2 }
				
genEquipInterfacesSdhAISAdmin OBJECT-TYPE
        SYNTAX EnableDisable
        ACCESS read-write
        STATUS mandatory
        DESCRIPTION
        "Enable, Disable AIS signaling at the V5 byte on the STM-1, OC-3 interface."
        ::= { genEquipInterfacesSdhEntry 3 }
				
genEquipInterfacesSdhTraceIdReceived OBJECT-TYPE
        SYNTAX DisplayString
        ACCESS read-only
        STATUS mandatory
        DESCRIPTION
        "J0 Trace Identifier signal that was received on the interface."
        ::= { genEquipInterfacesSdhEntry 4 }
				
genEquipInterfacesSdhTraceIdTransmitted OBJECT-TYPE
        SYNTAX DisplayString
        ACCESS read-write
        STATUS mandatory
        DESCRIPTION
        "J0 Trace Identifier signal that is transmitted on the interface."
        ::= { genEquipInterfacesSdhEntry 5 }
				
genEquipInterfacesSdhTraceIdExpected OBJECT-TYPE
        SYNTAX DisplayString
        ACCESS read-write
        STATUS mandatory
        DESCRIPTION
        "J0 Trace Identifier signal that is expected to be received on the interface."
        ::= { genEquipInterfacesSdhEntry 6 }
				
genEquipInterfacesSdhTraceIdStringLength OBJECT-TYPE
        SYNTAX INTEGER {
					len1(0),
					len15(1),
					len62(2)
		}
        ACCESS read-write
        STATUS mandatory
        DESCRIPTION
        "Trace identifier string length. Lengths 0 and 15 are valid for SDH systems. Length 62 is additionally available in SONET systems."
        ::= { genEquipInterfacesSdhEntry 7 }
				
genEquipInterfacesSdhExcessiveBer OBJECT-TYPE
        SYNTAX INTEGER { n1e-3(0), n1e-4(1), n1e-5(2) }
        ACCESS read-write
        STATUS mandatory
        DESCRIPTION
        "Excessive BER threshold on the interface."
        ::= { genEquipInterfacesSdhEntry 8 }
				
genEquipInterfacesSdhSignalDegrade OBJECT-TYPE
        SYNTAX INTEGER { n1e-6(3), n1e-7(4), n1e-8(5), n1e-9(6) }
        ACCESS read-write
        STATUS mandatory
        DESCRIPTION
        "Signal degrade threshold on the interface."
        ::= { genEquipInterfacesSdhEntry 9 }			

genEquipInterfacesSdhLoopback OBJECT-TYPE
        SYNTAX INTEGER {
        			off(0),
        			loopback-towards-system(1),
        			loopback-towards-line(2)
        }
        ACCESS read-write
        STATUS mandatory
        DESCRIPTION
        "SDH Loopback."
        ::= { genEquipInterfacesSdhEntry 10 }			
		
genEquipInterfacesSdhClockSourceStatus OBJECT-TYPE
        SYNTAX INTEGER {
					internal-clock(0),
					loop(1),
					synchronization-vc(2)
		}
        ACCESS read-only
        STATUS mandatory
        DESCRIPTION
        "The actual source of the clock for the outgoing STM-1/OC-3 signal. 
		It may differ from the desired source if the source signal is missing or corrupt"
        ::= { genEquipInterfacesSdhEntry 11 }
				
genEquipInterfacesSdhLineTxProtectionMode OBJECT-TYPE
        SYNTAX INTEGER {
				normal(1),
				uni-directional-MSP(2)
		}
        ACCESS read-write
        STATUS mandatory
        DESCRIPTION
        "this parameter configures the behavior of the transmitting line in a 1+1 HSB configuration. 
		In normal mode the stand-by signal is silenced. In uni-directional MSP both units will transmit"
        ::= { genEquipInterfacesSdhEntry 12 }			

genEquipInterfacesSdhSyncVC OBJECT-TYPE
        SYNTAX INTEGER (1..63)
        ACCESS read-write
        STATUS mandatory
        DESCRIPTION
        "The outgoing VC signal to be taken as the STM-1/OC-3 synchronization source if
      	genEquipInterfacesSdhClockSource is set to synchronization-vc"
        ::= { genEquipInterfacesSdhEntry 13 }			

		
-- LPVC (Low Oreder Path VC) 
genEquipInterfacesSdhLpVcTable  OBJECT-TYPE
        SYNTAX  SEQUENCE OF GenEquipInterfacesSdhLpVcEntry
        ACCESS  not-accessible
        STATUS mandatory
        DESCRIPTION
        "This table includes properties for each Low-order path VC (VC-11/12) in the SDH interface. "
        ::= { genEquipInterfacesSdh 2 }

genEquipInterfacesSdhLpVcEntry OBJECT-TYPE
        SYNTAX GenEquipInterfacesSdhLpVcEntry
        ACCESS not-accessible
        STATUS mandatory
          DESCRIPTION
         "This table includes properties for each Low-order path VC (VC-11/12) in the SDH interface. "
        INDEX { ifIndex, genEquipInterfacesSdhLpVcId }
        ::= { genEquipInterfacesSdhLpVcTable 1 }

GenEquipInterfacesSdhLpVcEntry ::=
		SEQUENCE {
			genEquipInterfacesSdhLpVcId
            	INTEGER,
			genEquipInterfacesSdhLpVcAIS
            	INTEGER
}

genEquipInterfacesSdhLpVcId OBJECT-TYPE
        SYNTAX INTEGER   (1..84)
        ACCESS read-only
        STATUS mandatory
        DESCRIPTION
        "VC-11 or VC-12 number; VCs are numbered according to standard KLM order. "
        ::= { genEquipInterfacesSdhLpVcEntry 1 }

genEquipInterfacesSdhLpVcAIS OBJECT-TYPE
        SYNTAX INTEGER {
          aisDetected(0), 
		  aisNotDetected(1) 
		}  
        ACCESS read-only
        STATUS mandatory
        DESCRIPTION
        "Indicates whether incoming AIS is currently detected in the VC's payload. 0 indicates that AIS is detected, 1 that is not detected."
        ::= { genEquipInterfacesSdhLpVcEntry 2 }

-- Interfaces AIS
genEquipInterfacesAIS	OBJECT IDENTIFIER ::= {genEquipInterfaces 5}

genEquipInterfacesAISAdmin OBJECT-TYPE
        SYNTAX EnableDisable
        ACCESS read-write
        STATUS mandatory
        DESCRIPTION
        "Control AIS Detection over all E1/T1/SDH ports."
        ::= { genEquipInterfacesAIS 1 }

-- Automatic State Propagation
genEquipInterfacesASP	OBJECT IDENTIFIER ::= {genEquipInterfaces 6}

genEquipInterfacesASPAdmin OBJECT-TYPE
        SYNTAX EnableDisable
        ACCESS read-write
        STATUS mandatory
        DESCRIPTION
        "Controls the Automatic State Propagation"
        ::= { genEquipInterfacesASP 1 }

genEquipInterfacesASPLocalLOC OBJECT-TYPE
        SYNTAX EnableDisable
        ACCESS read-write
        STATUS mandatory
        DESCRIPTION
        "Enables fault propagation upon detection of local LOC.
        This configuration is relevant only for non-protected single-pipe switch mode only."
        ::= { genEquipInterfacesASP 2 }

genEquipInterfacesASPLocalExcessiveBER  OBJECT-TYPE
        SYNTAX EnableDisable
        ACCESS read-write
        STATUS mandatory
        DESCRIPTION 
        "Enables fault propagation to the Ethernet interface upon detection of radio excessive BER.
 	   This configuration is relevant only for non-protected single-pipe switch mode only."

        ::= { genEquipInterfacesASP 3 }

genEquipInterfacesASPACMthreshold OBJECT-TYPE
        SYNTAX INTEGER {
				profile-0(0),
				profile-1(1),
				profile-2(2),
				profile-3(3),
				profile-4(4),
				profile-5(5),
				profile-6(6),
				profile-7(7)
		}
        ACCESS read-write
        STATUS mandatory
        DESCRIPTION
        "Enable or disable the propagation when Radio ACM profile degrades below a defined profile. 
         This configuration is relevant only for non-protected single-pipe switch mode only when ACM 
	   radio script is running."
        ::= { genEquipInterfacesASP 4 }

genEquipInterfacesASPRemoteFault  OBJECT-TYPE
        SYNTAX EnableDisable
        ACCESS read-write
        STATUS mandatory
        DESCRIPTION           	
        "This parameter enables/disables automatic state propagation.
	   The following remote faults are propagated to the NE by default:
        - Radio LOF
        - Radio link ID mismatch 
        - Ethernet line LOC
        any other remote faults are propagated to the NE only if they are 
        enabled at the local NE"
        ::= { genEquipInterfacesASP 5 }

-- Diagnostics and Maintenance
genEquipDiagAndMaintenance	OBJECT IDENTIFIER ::= {genEquip 10}

-- Radio Loopback

genEquipDiagAndMaintenanceRadioLoopbackTimeout		OBJECT-TYPE
		SYNTAX 		INTEGER (0..1440)
		ACCESS		read-write
        STATUS		mandatory
        DESCRIPTION
		"Radio loopback timeout, in minutes. 0 means no timer."
::= { genEquipDiagAndMaintenance 1 }


-- Line Loopback

genEquipDiagAndMaintenanceLineLoopbackTimeout		OBJECT-TYPE
		SYNTAX 		INTEGER (0..1440)
		ACCESS		read-write
        STATUS		mandatory
        DESCRIPTION
		"Line loopback timeout, in minutes. 0 means no timer."
::= { genEquipDiagAndMaintenance 2 }    

-- STM-1/OC-3

genEquipDiagAndMaintenanceSDHLoopbackTimeout		OBJECT-TYPE
		SYNTAX 		INTEGER (0..1440)
		ACCESS		read-write
        STATUS		mandatory
        DESCRIPTION
		"STM-1/OC-3 line loopback timeout, in minutes. 0 means no timer."
::= { genEquipDiagAndMaintenance 3 }


		

-- Security Configuration
genEquipSecurity	OBJECT IDENTIFIER ::= {genEquip 11}

-- Security Configuration
genEquipSecurityConfiguration	OBJECT IDENTIFIER ::= {genEquipSecurity 1}

genEquipSecurityCfgUploadPublicKeyStatus		OBJECT-TYPE
		SYNTAX 		ProgressStatus
		ACCESS		read-only
        STATUS		mandatory
        DESCRIPTION
		"The upload status of the Public key."
::= { genEquipSecurityConfiguration 1 }
		
genEquipSecurityCfgDownloadSecurityStatus		OBJECT-TYPE
		SYNTAX 		ProgressStatus
		ACCESS		read-only
        STATUS		mandatory
        DESCRIPTION
		"The download status of the digital certificate."
::= { genEquipSecurityConfiguration 2 }

genEquipSecurityCfgSecurityFileName		OBJECT-TYPE
		SYNTAX 		DisplayString
		ACCESS		read-write
        STATUS		mandatory
        DESCRIPTION
		"The certificate file name to be downloaded."
::= { genEquipSecurityConfiguration 3 }
		
genEquipSecurityCfgSecurityFileType		OBJECT-TYPE
		SYNTAX 		INTEGER {
						target-certificate(0),
						target-ca-certificate(1)
		}
		ACCESS		read-write
        STATUS		mandatory
        DESCRIPTION
		"The digital certificate file type."
::= { genEquipSecurityConfiguration 4 }
		
genEquipSecurityCfgSecurityFileFormat		OBJECT-TYPE
		SYNTAX 		INTEGER {
						pem(0),
						der(1)
		}
		ACCESS		read-write
        STATUS		mandatory
        DESCRIPTION
		"The certificate file format.
		.pem - (Privacy Enhanced Mail) Base64 encoded DER certificate,
		 enclosed between -----BEGIN CERTIFICATE----- and -----END CERTIFICATE-----
		 
		 .der is a subset of Basic Encoding Rules (BER) providing for exactly one way to encode an ASN.1 value."
::= { genEquipSecurityConfiguration 5 }
		
genEquipSecurityCfgSecurityWebCertificateAdmin		OBJECT-TYPE
		SYNTAX 		EnableDisable
		ACCESS		read-write
        STATUS		mandatory
        DESCRIPTION
		"The admin state of the certificate."
::= { genEquipSecurityConfiguration 6 }
		
genEquipSecurityCfgWebProtocol		OBJECT-TYPE
		SYNTAX 		INTEGER { 
						http(1), 
						https(2) 
		}
		ACCESS		read-write
        STATUS		mandatory
        DESCRIPTION
		"Use unsecure http or secure https."
::= { genEquipSecurityConfiguration 7 }
		
genEquipSecurityCfgTelnetAdmin		OBJECT-TYPE
		SYNTAX 		EnableDisable
		ACCESS		read-write
        STATUS		mandatory
        DESCRIPTION
		"Enable or disable the Telnet server on the NE."
::= { genEquipSecurityConfiguration 8 }
		
genEquipSecurityCfgAutoLogOutPeriod		OBJECT-TYPE
		SYNTAX 		INTEGER (1..60)
		ACCESS		read-write
        STATUS		mandatory
        DESCRIPTION
		"Auto logout period for CLI or web users, (1-60 seconds)"
::= { genEquipSecurityConfiguration 9 }

genEquipSecurityXFTP	OBJECT IDENTIFIER ::= {genEquipSecurityConfiguration 10}
		
genEquipSecurityXFTPHostIP		OBJECT-TYPE
		SYNTAX 		IpAddress
		ACCESS		read-write
        STATUS		mandatory
        DESCRIPTION
		"The FTP/SFTP host IP address."
::= { genEquipSecurityXFTP 1 }
		
genEquipSecurityXFTPHostPath		OBJECT-TYPE
		SYNTAX 		DisplayString
		ACCESS		read-write
        STATUS		mandatory
        DESCRIPTION
		"The FTP/SFTP host directory path."
::= { genEquipSecurityXFTP 2 }
		
genEquipSecurityXFTPProtocol		OBJECT-TYPE
		SYNTAX 		INTEGER { 
						ftp(0), 
						sftp(1) 
		}
		ACCESS		read-write
        STATUS		mandatory
        DESCRIPTION
		"Either FTP or SFTP to be used."
::= { genEquipSecurityXFTP 3 }
		
genEquipSecurityXFTPUserName		OBJECT-TYPE
		SYNTAX 		DisplayString
		ACCESS		read-write
        STATUS		mandatory
        DESCRIPTION
		"FTP User name."
::= { genEquipSecurityXFTP 4 }
		
genEquipSecurityXFTPPassword		OBJECT-TYPE
		SYNTAX 		DisplayString
		ACCESS		read-write
        STATUS		mandatory
        DESCRIPTION
		"FTP User password."
::= { genEquipSecurityXFTP 5 }

genEquipSecurityCfgPassFirstLoginChange		OBJECT-TYPE
		SYNTAX 		NoYes
		ACCESS		read-write
        STATUS		mandatory
        DESCRIPTION
		"Define whether user's first login will be required to change it password or not"
::= { genEquipSecurityConfiguration 11 }

genEquipSecurityCfgCSRCreation		OBJECT-TYPE
		SYNTAX 		DisplayString (SIZE(0..512))
		ACCESS		read-write
        STATUS		mandatory
        DESCRIPTION
		"This command create CSR file of the element. 
		The file could be uploaded to external server by using the genEquipMngFileTransferFileTypeOper OID.
		The command syntax should be: 
			<country_name> <state> <locality_name> <organization_name> <organization_unit_name> <common_name> <email_addr>. 
			All the fields must be referred, for skipping on any field, use 'symbol instead'."
::= { genEquipSecurityConfiguration 12 }

genEquipSecurityCfgWarningBannerFName  		OBJECT-TYPE
		SYNTAX		DisplayString
		ACCESS		read-write
		STATUS		mandatory
		DESCRIPTION
		"The Warning Banner file name to be downloaded to the NE."
::= {  genEquipSecurityConfiguration 13 }
		

-- Users and Groups
genEquipSecurityUsersAndGroups	OBJECT IDENTIFIER ::= {genEquipSecurity 2}

genEquipSecurityUsersTable  OBJECT-TYPE
        SYNTAX  SEQUENCE OF GenEquipSecurityUsersEntry
        ACCESS  not-accessible
        STATUS mandatory
        DESCRIPTION
        "User table."
        ::= { genEquipSecurityUsersAndGroups 1 }

genEquipSecurityUsersEntry OBJECT-TYPE
        SYNTAX GenEquipSecurityUsersEntry
        ACCESS not-accessible
        STATUS mandatory
          DESCRIPTION
          "User table."
        INDEX { genEquipSecurityUsersName }
        ::= { genEquipSecurityUsersTable 1 }

GenEquipSecurityUsersEntry ::=
		SEQUENCE {
			genEquipSecurityUsersName 
            	DisplayString,
			genEquipSecurityUsersPasswd 
            	DisplayString,
			genEquipSecurityUsersPriviledge 
            	INTEGER,
			genEquipSecurityUsersPasswdAging 
            	INTEGER,
			genEquipSecurityUsersExprDate 
            	INTEGER,
			genEquipSecurityUsersLastLogin
            	INTEGER,
			genEquipSecurityUsersRowStatus 
            	RowStatus
}

genEquipSecurityUsersName		OBJECT-TYPE
		SYNTAX 		DisplayString
		ACCESS		read-write
        STATUS		mandatory
        DESCRIPTION
		"This value is the user name."
::= { genEquipSecurityUsersEntry 1 }
		
genEquipSecurityUsersPasswd		OBJECT-TYPE
		SYNTAX 		DisplayString
		ACCESS		read-write
        STATUS		mandatory
        DESCRIPTION
		"This value is the user's password. It is used only in the creation phase. To change the password, 
		 you need to use the genEquipSecurityUsersAndGroupsChangePasswd command"
::= { genEquipSecurityUsersEntry 2 }
		
genEquipSecurityUsersPriviledge		OBJECT-TYPE
		SYNTAX 		INTEGER {
							no-privilege-lvl(-1),
							viewer-user-lvl(0),
							operator-user-lvl(1),
							admin-user-lvl(2),
							tech-user-lvl(3) 
		}
		ACCESS		read-write
        STATUS		mandatory
        DESCRIPTION
		"This value is the users privilege."
::= { genEquipSecurityUsersEntry 3 }
		
genEquipSecurityUsersPasswdAging		OBJECT-TYPE
		SYNTAX 		INTEGER (0..90)
		ACCESS		read-write
        STATUS		mandatory
        DESCRIPTION
		"This value is the user's password aging time (in days). When response is 99999 the meaning is No Aging."
::= { genEquipSecurityUsersEntry 4 }
		
genEquipSecurityUsersExprDate		OBJECT-TYPE
		SYNTAX 		INTEGER
		ACCESS		read-write
        STATUS		mandatory
        DESCRIPTION
		"This value is the user's password expiration date. 
		The value is presented in time_t format. When response is -1 the meaning is Never Expired."
::= { genEquipSecurityUsersEntry 5 }
		
genEquipSecurityUsersLastLogin		OBJECT-TYPE
		SYNTAX 		INTEGER
		ACCESS		read-only
        STATUS		mandatory
        DESCRIPTION
		"This value is the user last login date. Time in seconds since January 1, 1970 00:00 UTC."
::= { genEquipSecurityUsersEntry 6 }
		
genEquipSecurityUsersRowStatus		OBJECT-TYPE
		SYNTAX 		RowStatus
		ACCESS		read-write
        STATUS		mandatory
        DESCRIPTION
		"This value is the status of the entry."
::= { genEquipSecurityUsersEntry 30 }
		
-- User password chnage as a single command
genEquipSecurityUsersAndGroupsChangePasswd		OBJECT-TYPE
		SYNTAX 		DisplayString
		ACCESS		read-write
        STATUS		mandatory
        DESCRIPTION
		"This command changes the user password at the command line. It takes all arguments as the command.
		It cannot be done through the table since it needs to provide the old password as well.
		The format is: '<username> <old-password> <new-password>' seperated with spaces."
::= { genEquipSecurityUsersAndGroups 2 }

-- SNMP Security params
genEquipSecuritySNMP	OBJECT IDENTIFIER ::= {genEquipSecurity 3}

genEquipSecuritySNMPReadCommunity		OBJECT-TYPE
		SYNTAX 		DisplayString
		ACCESS		read-write
        STATUS		mandatory
        DESCRIPTION
		"This is the SNMP Read community string"
::= { genEquipSecuritySNMP 1 }

genEquipSecuritySNMPWriteCommunity		OBJECT-TYPE
		SYNTAX 		DisplayString
		ACCESS		read-write
        STATUS		mandatory
        DESCRIPTION
		"This is the SNMP Write community string"
::= { genEquipSecuritySNMP 2 }

		
-- ###########################################################
--                 Traps Section
-- ###########################################################

alarmTrap TRAP-TYPE
		ENTERPRISE microwave-radio
		VARIABLES { genEquipCurrentAlarmCounter,
					genEquipCurrentAlarmRaisedTimeT,
					genEquipCurrentAlarmId,
					genEquipCurrentAlarmSlotId,
					genEquipCurrentAlarmInstance, 										
		            genEquipCurrentAlarmSeverity, 
		            genEquipCurrentAlarmIfIndex,
		            genEquipCurrentAlarmModule,
		            genEquipCurrentAlarmDesc,
					genEquipMostSevereAlarm,
					genEquipNetworkAgentIp,
					genEquipCurrentAlarmState,
					genEquipTrapCfgMgrCLLI					
		          }
		DESCRIPTION "Alarm network trap"
		::= 1001

eventTrap TRAP-TYPE
		ENTERPRISE microwave-radio
		VARIABLES { genEquipCurrentAlarmCounter,
					genEquipCurrentAlarmRaisedTimeT,
					genEquipCurrentAlarmId,
					genEquipCurrentAlarmSlotId, 
					genEquipCurrentAlarmInstance, 										
		            genEquipCurrentAlarmSeverity, 
		            genEquipCurrentAlarmIfIndex,
		            genEquipCurrentAlarmModule,
		            genEquipCurrentAlarmDesc,
					genEquipMostSevereAlarm,
					genEquipNetworkAgentIp,
					genEquipTrapCfgMgrCLLI
		          }
		DESCRIPTION "Event network trap"
		::= 1002
		
		
heartbeatTrap TRAP-TYPE
		ENTERPRISE microwave-radio
		VARIABLES { genEquipTrapCfgMgrCLLI
		          }
		DESCRIPTION "The heartbeat trap, sent once per heartbeat period"
		::= 1003

eventTrapSTP TRAP-TYPE        -- STP, RSTP, Ring RSTP trap
       ENTERPRISE microwave-radio
       VARIABLES { genEquipCurrentAlarmCounter,           -- general event parameters
                   genEquipCurrentAlarmRaisedTimeT,
                   genEquipCurrentAlarmId,
                   genEquipCurrentAlarmSlotId,
                   genEquipCurrentAlarmInstance,                                                                           
                   genEquipCurrentAlarmSeverity,
                   genEquipCurrentAlarmIfIndex,
                   genEquipCurrentAlarmModule,
                   genEquipCurrentAlarmDesc, -- This field shows show the descriptions of the event
                                             -- "STP event - on port: <port>, root id: <root id>, Bridge role: <bridge role>,
                                             --  Role: <Role>, State: <state>"      
                   genEquipMostSevereAlarm,
                   genEquipNetworkAgentIp,
                   genEquipTrapCfgMgrCLLI,
                   genEquipEthernetSwitchXSTPParamsEthernetPortsRole,   -- event trigger
                   genEquipEthernetSwitchXSTPParamsEthernetPortsState,       -- event trigger       
                   genEquipEthernetSwitchXSTPBridgeRole,  
                   genEquipEthernetSwitchXSTPRootID    -- RSTP parameters
                 }
       DESCRIPTION "STP trap.
                    (1) The description field shows show the descriptions of the event
                    STP event - on port: <port>, root id: <root id>, Bridge role: <bridge role>,
                    Role: <Role>, State: <state>                       
                    In addition to the general trap event var-binds, this trap also adds the STP parameters."  
                               
       ::= 1004

genTraps OBJECT IDENTIFIER ::= { microwave-radio 11 }
		generalV3Trap NOTIFICATION-TYPE
		OBJECTS { 	genEquipCurrentAlarmCounter,
					genEquipCurrentAlarmRaisedTimeT,
					genEquipCurrentAlarmId, 
					genEquipCurrentAlarmSlotId,
					genEquipCurrentAlarmInstance, 										
		            genEquipCurrentAlarmSeverity, 
		            genEquipCurrentAlarmIfIndex,
		            genEquipCurrentAlarmModule,
		            genEquipCurrentAlarmDesc,
					genEquipMostSevereAlarm,
					genEquipNetworkAgentIp,
					genEquipCurrentAlarmState,
					genEquipTrapCfgMgrCLLI
		          }
		STATUS	current
		DESCRIPTION "General network V3 trap"
		::= { genTraps 1 }

		eventV3Trap NOTIFICATION-TYPE
		OBJECTS { 	genEquipCurrentAlarmCounter,
					genEquipCurrentAlarmRaisedTimeT,
					genEquipCurrentAlarmId, 
					genEquipCurrentAlarmSlotId,
					genEquipCurrentAlarmInstance, 										
		            genEquipCurrentAlarmSeverity, 
		            genEquipCurrentAlarmIfIndex,
		            genEquipCurrentAlarmModule,
		            genEquipCurrentAlarmDesc,
					genEquipMostSevereAlarm,
					genEquipNetworkAgentIp,
					genEquipTrapCfgMgrCLLI
		          }
		STATUS	current
		DESCRIPTION "Event network V3 trap"
		::= { genTraps 2 }

		heartbeatV3Trap NOTIFICATION-TYPE
		OBJECTS     {     
				genEquipTrapCfgMgrCLLI
					}

             STATUS  current
             DESCRIPTION
				"Heartbeat v3 trap - The heartbeat trap, sent once per heartbeat period"  
	 ::= { genTraps 3 }

      eventv3TrapSTP NOTIFICATION-TYPE        -- STP, RSTP, Ring RSTP trap
        OBJECTS    { genEquipCurrentAlarmCounter,           -- general event parameters
                     genEquipCurrentAlarmRaisedTimeT,
                     genEquipCurrentAlarmId,
                     genEquipCurrentAlarmSlotId,
                     genEquipCurrentAlarmInstance,                                                                           
                     genEquipCurrentAlarmSeverity,
                     genEquipCurrentAlarmIfIndex,
                     genEquipCurrentAlarmModule,
                     genEquipCurrentAlarmDesc, -- This field shows show the descriptions of the event
                                               -- "STP event - on port: <port>, root id: <root id>, Bridge role: <bridge role>,
                                               --  Role: <Role>, State: <state>,
                     genEquipMostSevereAlarm,
                     genEquipNetworkAgentIp,
                     genEquipTrapCfgMgrCLLI,
                     genEquipEthernetSwitchXSTPParamsEthernetPortsRole,   -- event trigger
                     genEquipEthernetSwitchXSTPParamsEthernetPortsState,       -- event trigger       
                     genEquipEthernetSwitchXSTPBridgeRole,  
                     genEquipEthernetSwitchXSTPRootID    -- RSTP parameters
                   }  
                STATUS  current
                DESCRIPTION "STP trap.
                             (1) The description field shows show the descriptions of the event
                             STP event - on port: <port>, root id: <root id>, Bridge role: <bridge role>,
                             Role: <Role>, State: <state>,
                             In addition to the general trap event var-binds, this trap also adds the STP parameters."
     ::= { genTraps 4 } 
	 
END
